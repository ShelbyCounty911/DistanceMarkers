FME workspace DistanceMarkers.fmw
Title: Distance Markers
Description: Distance Markers ETL (FME Form)
This FME Form workspace collects public distance-marker datasets, standardizes them into a shared schema, generates alternate search names, and publishes the results to ArcGIS Online.
Sources
The workspace currently uses public ArcGIS REST services for:
Tennessee DOT mile markers
FRA rail mileposts
USACE river mile markers
Shelby County 911 ESZ polygons
Shelby County 911 trail markers
Current source filters:
TDOT Mile Markers: COUNTY=79
FRA Rail Posts: STCYFIPS=47157
USACE River Mile Markers: RIVER_NUMB=21
SC911 ESZ: 1=1
SC911 Trail Markers: 1=1
Outputs
The workspace writes to these ArcGIS Online layers/tables:
DistanceMarkers — core marker features
DistanceMarker_AltNames — alternate names for road, rail, and river markers
TrailMarker_AltNames — alternate names for trail markers
What the workspace does
Standardizes multiple marker types
The workspace maps several source datasets into a shared marker model with values such as:
ShelbyID
Type
Marker
MarkerExt
Name
Label
Current standardized marker types include:
Road
Railroad
River
Trail
Parses TDOT road marker text
The TDOT branch performs the most custom transformation work. It:
filters to relevant sign records
parses COMMENTS
splits compound text into elements
normalizes route and direction abbreviations
builds a standardized road marker label
Examples of normalization include:
N → North
S → South
E → East
W → West
SR... → State Route ...
I... → Interstate ...
Note: the 2-element TDOT parsing path is currently skipped because the source values are too inconsistent to map cleanly.
Spatially filters river markers
River mile markers are spatially constrained using the SC911 ESZ layer:
ESZ polygons are dissolved
the result is buffered by 5 miles
USACE river markers are clipped to that buffered area
only features inside the buffered area are kept
Generates alternate search names
The workspace creates alternate-name records for locator/search support by:
building a list of spelling and wording variations
exploding the list into one record per alternate name
removing geometry
writing the result to dedicated alternate-name tables
Examples include variations using:
Mile
Mile Marker
MM
abbreviated vs expanded route names
reversed marker/name ordering
Deduplicates selected branches
Duplicate handling is source-specific:
road markers: deduplicated by ShelbyID
trail markers: deduplicated by ShelbyID
rail markers: no duplicates expected by design
river markers: no duplicates expected by design
Workspace structure
TDOT Mile Markers
Parses and standardizes road mile marker text from COMMENTS, then creates alternate-name records.
FRA Rail Posts
Maps MILEPOST values into the common schema and creates alternate-name records.
USACE River Mile Markers
Filters river markers spatially using buffered ESZ geometry, standardizes the schema, and creates alternate-name records.
SC911 ESZ
Creates dissolved and buffered support geometry for river filtering.
SC911 Trail Markers
Standardizes trail marker attributes, removes duplicate core records, and creates alternate-name records.
Dependencies
FME Form
configured ArcGIS Online web connections
public ArcGIS REST endpoints used by the custom source transformers
ArcGIS feature service writer support used by the workspace
Maintenance notes
When updating this workspace, review:
upstream source availability
source schema changes
ArcGIS Online destination schema
TDOT parsing assumptions
alternate-name generation rules
river spatial filter assumptions
ShelbyID logic used for joins and deduplication
Notes
The TDOT parsing logic is highly customized and regex-heavy.
ShelbyID is used as the core join key between the main marker output and alternate-name outputs.
The workspace uses separate outputs for core marker features and alternate-name records.
Hosted ArcGIS Online schema changes may require writer schema refresh or feature type re-import.
License / data usage
This repository contains FME workspace logic only.
Usage rights and attribution for source datasets depend on the original data publishers. Review the licensing and attribution requirements of each upstream service before redistribution or republication.
Usage: For help with this workspace, reach out to:
Maps@ShelbyCounty911.org
History: 20260820,Bruno Blanco,Original public release

Parameters:
- MESSAGE_1 =

Writers:
- SAFE.ESRI-AGOL.ARCGISFEATURESERVICE_1: SAFE.ESRI-AGOL.ARCGISFEATURESERVICE
- SAFE.ESRI-AGOL.ARCGISFEATURESERVICE_2: SAFE.ESRI-AGOL.ARCGISFEATURESERVICE
- SAFE.ESRI-AGOL.ARCGISFEATURESERVICE_3: SAFE.ESRI-AGOL.ARCGISFEATURESERVICE

Note: Used for clipping and to extract CITY attributes via point-in-polygon lookups
SC911_ESZ: GET from REST
    TARGET_URL = https://services6.arcgis.com/FStub7HlCSCdqoXK/arcgis/rest/services/OpenDataESN/FeatureServer/0
    WHERE_QUERY = 1=1
    -> TDOT_mm_clipper [CLIPPER]
    -> FRA_ESZ_clipper [CLIPPER]
    -> USACE_Clipper [CLIPPER]
    -> HullAccumulator
    -> trail_markers_clipper [CLIPPER]
TDOT_Mile_Markers: GET from REST
    TARGET_URL = https://services2.arcgis.com/nf3p7v7Zy4fTOh6M/arcgis/rest/services/Mile_Marker/FeatureServer/0
    WHERE_QUERY = COUNTY=79
    -> expose_attrs
Note: Select the features we actual need
filter_results: Tester
    BOOL_OP = COMPOSITE
    COMPOSITE_TEST = 1 AND 2
    TEST_CLAUSE:
      TEST @Value(MUTCD) = TN-45A
      TEST COMMENTS ATTRIBUTE_HAS_A_VALUE ""
    TEST_MODE = TEST
    PASSED -> TDOT_mm_clipper [CANDIDATE]
Note: Extract CITY attr
TDOT_mm_clipper: Clipper
    ADD_NODATA = YES
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> expose_attrs_5
    OUTSIDE -> expose_attrs_5
Note: Exclude unnecessary index element to simplify logic down the line
remove_unnecessary: StringReplacer
    CASE = NO
    NO_MATCH = _FME_NO_OP_
    REGEXP = YES
    STR_REPLACE_TABLE = "COMMENTS MILE; <pipe>\\sMILE\\s "
    -> split_on_semicolon
Note: Split incoming structured text field into different elements
split_on_semicolon: AttributeSplitter
    ATTR_NAME = COMMENTS
    DELIMITER = ;
    DROP_EMPTY_PARTS = NO
    LIST_NAME = _sign_text
    TRIM_TYPE = BOTH
    -> count_list_elements
Note: Count the elements that are coming in so we can split the data into different streams
count_list_elements: ListElementCounter
    CNT_ATTR = _element_count
    LIST_NAME = _sign_text{}
    -> split_on_no_of_elements
Note: Split into different streams based on the number of elements that are coming in
split_on_no_of_elements: TestFilter
    DEFAULT_VALUE = PENDING ERROR
    PASSED_TEST_GROUP_OUTPUT = FIRST
    TEST_LIST = "BOOL_OP,OR,COMPOSITE_TEST,""""""1"""""",TEST_CLAUSE,TEST @Value(_element_count) = 4",4,"BOOL_OP,OR,COMPOSITE_TEST,""""""1"""""",TEST_CLAUSE,TEST @Value(_element_count) = 3",3,"BOOL_OP,OR,COMPOSITE_TEST,""""""1"""""",TEST_CLAUSE,TEST @Value(_element_count) = 2",2
    4 -> split_on_colon
    3 -> split_on_colon_2
    2 -> Junction_2
Note: Split substring into elements (e.g.: 45 .2
split_on_colon: AttributeSplitter
    ATTR_NAME = _sign_text{3}
    DELIMITER = :
    DROP_EMPTY_PARTS = NO
    LIST_NAME = _sign_text_ext
    TRIM_TYPE = BOTH
    -> rmv_spec_characters
Note: Remove spec characters that are not regex safe: / .()[]{}^$\|?,:
rmv_spec_characters: StringReplacer
    CASE = NO
    NO_MATCH = _FME_NO_OP_
    REGEXP = NO
    STR_REPLACE_TABLE = _sign_text{2}      _sign_text{2} .  _sign_text{2} )  _sign_text{2} (  _sign_text{2} ]  _sign_text{2} [  _sign_text{2} }  _sign_text{2} {  _sign_text{2} ^  _sign_text{2} $  _sign_text{2} \  _sign_text{2} <pipe>  _sign_text{2} ?  _sign_text{2} :  _sign_text{3}      _sign_text{3} .  _sign_text{3} )  _sign_text{3} (  _sign_text{3} ]  _sign_text{3} [  _sign_text{3} }  _sign_text{3} {  _sign_text{3} ^  _sign_text{3} $  _sign_text{3} \  _sign_text{3} <pipe>  _sign_text{3} ?  _sign_text{3} :
    -> string_manipulation
Note: Note: / Using a lot of regex here. Be sure to double check all changes
string_manipulation: AttributeCreator
    ATTR_TABLE:
      SET_TO _primname (varchar(100)) = FME_CONDITIONAL:DEFAULT_VALUE'ERROR'BOOL_OP;OR;COMPOSITE_TEST;1;CASE_INSENSITIVE_TEST @Value(_sign_text{1}) CONTAINS_REGEX (?:STATE ROUTE<pipe>SR)[-\s]*'@ReplaceRegularExpression(@Value(_sign_text{1}),(?:STATE ROUTE<pipe>SR)[-\s]*,"State Route ",caseSensitive=False)'BOOL_OP;OR;COMPOSITE_TEST;1;CASE_INSENSITIVE_TEST @Value(_sign_text{1}) CONTAINS_REGEX (?:INTERSTATE<pipe>I)[-\s]*'@ReplaceRegularExpression(@Value(_sign_text{1}),(?:INTERSTATE<pipe>I)[-\s]*,"Interstate ",caseSensitive=False)'FME_NUM_CONDITIONS3___
      SET_TO _altname0 (varchar(200)) = FME_CONDITIONAL:DEFAULT_VALUE'ERROR'BOOL_OP;OR;COMPOSITE_TEST;1;CASE_INSENSITIVE_TEST @Value(_sign_text{1}) CONTAINS_REGEX (?:STATE ROUTE<pipe>SR)[-\s]*'@ReplaceRegularExpression(@Value(_sign_text{1}),(?:STATE ROUTE<pipe>SR)[-\s]*,"SR-",caseSensitive=False)'BOOL_OP;OR;COMPOSITE_TEST;1;CASE_INSENSITIVE_TEST @Value(_sign_text{1}) CONTAINS_REGEX (?:INTERSTATE<pipe>I)[-\s]*'@ReplaceRegularExpression(@Value(_sign_text{1}),(?:INTERSTATE<pipe>I)[-\s]*,"I-",caseSensitive=False)'FME_NUM_CONDITIONS3___
      SET_TO _altname1 (varchar(200)) = FME_CONDITIONAL:DEFAULT_VALUE'ERROR'BOOL_OP;OR;COMPOSITE_TEST;1;CASE_INSENSITIVE_TEST @Value(_sign_text{1}) CONTAINS_REGEX (?:STATE ROUTE<pipe>SR)[-\s]*'@ReplaceRegularExpression(@Value(_sign_text{1}),(?:STATE ROUTE<pipe>SR)[-\s]*,"SR ",caseSensitive=False)'BOOL_OP;OR;COMPOSITE_TEST;1;CASE_INSENSITIVE_TEST @Value(_sign_text{1}) CONTAINS_REGEX (?:INTERSTATE<pipe>I)[-\s]*'@ReplaceRegularExpression(@Value(_sign_text{1}),(?:INTERSTATE<pipe>I)[-\s]*,"I ",caseSensitive=False)'FME_NUM_CONDITIONS3___
      SET_TO _altname2 (varchar(200)) = FME_CONDITIONAL:DEFAULT_VALUE'ERROR'BOOL_OP;OR;COMPOSITE_TEST;1;CASE_INSENSITIVE_TEST @Value(_sign_text{1}) CONTAINS_REGEX (?:STATE ROUTE<pipe>SR)[-\s]*'@ReplaceRegularExpression(@Value(_sign_text{1}),(?:STATE ROUTE<pipe>SR)[-\s]*,"SR",caseSensitive=False)'BOOL_OP;OR;COMPOSITE_TEST;1;CASE_INSENSITIVE_TEST @Value(_sign_text{1}) CONTAINS_REGEX (?:INTERSTATE<pipe>I)[-\s]*'@ReplaceRegularExpression(@Value(_sign_text{1}),(?:INTERSTATE<pipe>I)[-\s]*,"I",caseSensitive=False)'FME_NUM_CONDITIONS3___
      SET_TO _altname3 (varchar(200)) = FME_CONDITIONAL:DEFAULT_VALUE'ERROR'BOOL_OP;OR;COMPOSITE_TEST;1;CASE_INSENSITIVE_TEST @Value(_sign_text{1}) CONTAINS_REGEX (?:STATE ROUTE<pipe>SR)[-\s]*'@ReplaceRegularExpression(@Value(_sign_text{1}),(?:STATE ROUTE<pipe>SR)[-\s]*,"",caseSensitive=False)'BOOL_OP;OR;COMPOSITE_TEST;1;CASE_INSENSITIVE_TEST @Value(_sign_text{1}) CONTAINS_REGEX (?:INTERSTATE<pipe>I)[-\s]*'@ReplaceRegularExpression(@Value(_sign_text{1}),(?:INTERSTATE<pipe>I)[-\s]*,"",caseSensitive=False)'FME_NUM_CONDITIONS3___
      SET_TO _direction_full (varchar(200)) = FME_CONDITIONAL:DEFAULT_VALUE'@FullTitleCase(@Value(_sign_text{0}))'BOOL_OP;OR;COMPOSITE_TEST;1;CASE_INSENSITIVE_TEST @Value(_sign_text{0}) CONTAINS_REGEX (\s*<pipe>^)\bN\b(\s*<pipe>$)'@ReplaceRegularExpression(@Value(_sign_text{0}),(\s*<pipe>^)\bN\b(\s*<pipe>$),"North",caseSensitive=False)'BOOL_OP;OR;COMPOSITE_TEST;1;CASE_INSENSITIVE_TEST @Value(_sign_text{0}) CONTAINS_REGEX (\s*<pipe>^)\bS\b(\s*<pipe>$)'@ReplaceRegularExpression(@Value(_sign_text{0}),(\s*<pipe>^)\bS\b(\s*<pipe>$),"South",caseSensitive=False)'BOOL_OP;OR;COMPOSITE_TEST;1;CASE_INSENSITIVE_TEST @Value(_sign_text{0}) CONTAINS_REGEX (\s*<pipe>^)\bE\b(\s*<pipe>$)'@ReplaceRegularExpression(@Value(_sign_text{0}),(\s*<pipe>^)\bE\b(\s*<pipe>$),"East",caseSensitive=False)'BOOL_OP;OR;COMPOSITE_TEST;1;CASE_INSENSITIVE_TEST @Value(_sign_text{0}) CONTAINS_REGEX (\s*<pipe>^)\bW\b(\s*<pipe>$)'@ReplaceRegularExpression(@Value(_sign_text{0}),(\s*<pipe>^)\bW\b(\s*<pipe>$),"West",caseSensitive=False)'FME_NUM_CONDITIONS5___
      SET_TO _direction_abbr (varchar(200)) = FME_CONDITIONAL:DEFAULT_VALUE'@FullTitleCase(@Value(_sign_text{0}))'BOOL_OP;OR;COMPOSITE_TEST;1;CASE_INSENSITIVE_TEST @Value(_sign_text{0}) CONTAINS_REGEX (\s*<pipe>^)\bNorth\b(\s*<pipe>$)'@ReplaceRegularExpression(@Value(_sign_text{0}),(\s*<pipe>^)\bNorth\b(\s*<pipe>$),"N",caseSensitive=False)'BOOL_OP;OR;COMPOSITE_TEST;1;CASE_INSENSITIVE_TEST @Value(_sign_text{0}) CONTAINS_REGEX (\s*<pipe>^)\bSouth\b(\s*<pipe>$)'@ReplaceRegularExpression(@Value(_sign_text{0}),(\s*<pipe>^)\bSouth\b(\s*<pipe>$),"S",caseSensitive=False)'BOOL_OP;OR;COMPOSITE_TEST;1;CASE_INSENSITIVE_TEST @Value(_sign_text{0}) CONTAINS_REGEX (\s*<pipe>^)\bEast\b(\s*<pipe>$)'@ReplaceRegularExpression(@Value(_sign_text{0}),(\s*<pipe>^)\bEast\b(\s*<pipe>$),"E",caseSensitive=False)'BOOL_OP;OR;COMPOSITE_TEST;1;CASE_INSENSITIVE_TEST @Value(_sign_text{0}) CONTAINS_REGEX (\s*<pipe>^)\bWest\b(\s*<pipe>$)'@ReplaceRegularExpression(@Value(_sign_text{0}),(\s*<pipe>^)\bWest\b(\s*<pipe>$),"W",caseSensitive=False)'FME_NUM_CONDITIONS5___
      SET_TO _marker_pt1 (varchar(200)) = @Value(_sign_text{2})
      SET_TO _marker_pt2 (varchar(200)) = @Value(_sign_text{3})
    INPUT_PORT_CONNECTED = CONNECTED
    -> if_error
Note: Exclude errors
if_error: Tester
    BOOL_OP = OR
    TEST_CLAUSE = TEST @Value(_primname) NOT_= ERROR
    TEST_MODE = TEST
    PASSED -> AttributeManager
    FAILED -> Junction
Note: Create and populate all final core fields. / Note: Also including several AltName fields in the final schema for use in POI locators
AttributeManager
    ATTR_TABLE:
      SET_TO DiscrpAgID (varchar(100)) = slbytnec1.shelby.tn.us
      SET_TO DateUpdate (datetime) = @CurrentDateTime()
      SET_TO NGUID (varchar(254)) = @Value(_sign_text{0})-@Value(_sign_text{1})-@Value(_sign_text{2})-@Value(_sign_text{3})
      SET_TO DM_Unit (varchar(15)) = Mile
      SET_TO DM_Value (number(9,3)) = FME_CONDITIONAL:DEFAULT_VALUE'@Value(_marker_pt1).@Value(_marker_pt2)'BOOL_OP;OR;COMPOSITE_TEST;1;CASE_SENSITIVE_TEST @Value(_marker_pt1) CONTAINS_REGEX [a-zA-Z]'FME_NULL_VALUE'FME_NUM_CONDITIONS2___
      SET_TO DM_Rte (varchar(100)) = @Value(_primname) @Value(_direction_full)
      SET_TO DM_Type (varchar(50)) = Road
      SET_TO DM_Ind (varchar(1)) = P
      SET_TO DM_Label (varchar(100)) = @Value(DM_Rte) Mile @Value(_sign_text{2}).@Value(_sign_text{3})
      SET_TO Area (varchar(100)) = @FullTitleCase(@Value(CITY))
      REMOVE COMMENTS (varchar(254))
      REMOVE MUTCD (varchar(25))
      REMOVE _sign_text{} (varchar(200))
      REMOVE _element_count (uint64)
      REMOVE _sign_text_ext{} (varchar(200))
      REMOVE CITY (varchar(100))
      REMOVE LOG_MILE (real64)
    -> if_alphanumeric
split_on_colon_2: AttributeSplitter
    ATTR_NAME = _sign_text{2}
    DELIMITER = :
    DROP_EMPTY_PARTS = NO
    LIST_NAME = _sign_text_ext
    TRIM_TYPE = BOTH
    -> rmv_spec_characters_3
rmv_spec_characters_3: StringReplacer
    CASE = NO
    NO_MATCH = _FME_NO_OP_
    REGEXP = NO
    STR_REPLACE_TABLE = _sign_text_ext{0}      _sign_text_ext{0} .  _sign_text_ext{0} )  _sign_text_ext{0} (  _sign_text_ext{0} ]  _sign_text_ext{0} [  _sign_text_ext{0} }  _sign_text_ext{0} {  _sign_text_ext{0} ^  _sign_text_ext{0} $  _sign_text_ext{0} \  _sign_text_ext{0} <pipe>  _sign_text_ext{0} ?  _sign_text_ext{0} :  _sign_text_ext{1}      _sign_text_ext{1} .  _sign_text_ext{1} )  _sign_text_ext{1} (  _sign_text_ext{1} ]  _sign_text_ext{1} [  _sign_text_ext{1} }  _sign_text_ext{1} {  _sign_text_ext{1} ^  _sign_text_ext{1} $  _sign_text_ext{1} \  _sign_text_ext{1} <pipe>  _sign_text_ext{1} ?  _sign_text_ext{1} :
    -> rmv_extraneous_str
rmv_extraneous_str: StringReplacer
    CASE = NO
    NO_MATCH = _FME_NO_OP_
    REGEXP = YES
    STR_REPLACE_TABLE = _sign_text_ext{0} [A-Z]{2,}  _sign_text_ext{1} [A-Z]{2,}
    -> string_manipulation_2
string_manipulation_2: AttributeCreator
    ATTR_TABLE:
      SET_TO _primname (varchar(100)) = FME_CONDITIONAL:DEFAULT_VALUE'ERROR'BOOL_OP;OR;COMPOSITE_TEST;1;CASE_INSENSITIVE_TEST @Value(_sign_text{1}) CONTAINS_REGEX (?:STATE ROUTE<pipe>SR)[-\s]*'@ReplaceRegularExpression(@Value(_sign_text{1}),(?:STATE ROUTE<pipe>SR)[-\s]*,"State Route ",caseSensitive=False)'BOOL_OP;OR;COMPOSITE_TEST;1;CASE_INSENSITIVE_TEST @Value(_sign_text{1}) CONTAINS_REGEX (?:INTERSTATE<pipe>I)[-\s]*'@ReplaceRegularExpression(@Value(_sign_text{1}),(?:INTERSTATE<pipe>I)[-\s]*,"Interstate ",caseSensitive=False)'FME_NUM_CONDITIONS3___
      SET_TO _altname0 (varchar(200)) = FME_CONDITIONAL:DEFAULT_VALUE'ERROR'BOOL_OP;OR;COMPOSITE_TEST;1;CASE_INSENSITIVE_TEST @Value(_sign_text{1}) CONTAINS_REGEX (?:STATE ROUTE<pipe>SR)[-\s]*'@ReplaceRegularExpression(@Value(_sign_text{1}),(?:STATE ROUTE<pipe>SR)[-\s]*,"SR-",caseSensitive=False)'BOOL_OP;OR;COMPOSITE_TEST;1;CASE_INSENSITIVE_TEST @Value(_sign_text{1}) CONTAINS_REGEX (?:INTERSTATE<pipe>I)[-\s]*'@ReplaceRegularExpression(@Value(_sign_text{1}),(?:INTERSTATE<pipe>I)[-\s]*,"I-",caseSensitive=False)'FME_NUM_CONDITIONS3___
      SET_TO _altname1 (varchar(200)) = FME_CONDITIONAL:DEFAULT_VALUE'ERROR'BOOL_OP;OR;COMPOSITE_TEST;1;CASE_INSENSITIVE_TEST @Value(_sign_text{1}) CONTAINS_REGEX (?:STATE ROUTE<pipe>SR)[-\s]*'@ReplaceRegularExpression(@Value(_sign_text{1}),(?:STATE ROUTE<pipe>SR)[-\s]*,"SR ",caseSensitive=False)'BOOL_OP;OR;COMPOSITE_TEST;1;CASE_INSENSITIVE_TEST @Value(_sign_text{1}) CONTAINS_REGEX (?:INTERSTATE<pipe>I)[-\s]*'@ReplaceRegularExpression(@Value(_sign_text{1}),(?:INTERSTATE<pipe>I)[-\s]*,"I ",caseSensitive=False)'FME_NUM_CONDITIONS3___
      SET_TO _altname2 (varchar(200)) = FME_CONDITIONAL:DEFAULT_VALUE'ERROR'BOOL_OP;OR;COMPOSITE_TEST;1;CASE_INSENSITIVE_TEST @Value(_sign_text{1}) CONTAINS_REGEX (?:STATE ROUTE<pipe>SR)[-\s]*'@ReplaceRegularExpression(@Value(_sign_text{1}),(?:STATE ROUTE<pipe>SR)[-\s]*,"SR",caseSensitive=False)'BOOL_OP;OR;COMPOSITE_TEST;1;CASE_INSENSITIVE_TEST @Value(_sign_text{1}) CONTAINS_REGEX (?:INTERSTATE<pipe>I)[-\s]*'@ReplaceRegularExpression(@Value(_sign_text{1}),(?:INTERSTATE<pipe>I)[-\s]*,"I",caseSensitive=False)'FME_NUM_CONDITIONS3___
      SET_TO _altname3 (varchar(200)) = FME_CONDITIONAL:DEFAULT_VALUE'ERROR'BOOL_OP;OR;COMPOSITE_TEST;1;CASE_INSENSITIVE_TEST @Value(_sign_text{1}) CONTAINS_REGEX (?:STATE ROUTE<pipe>SR)[-\s]*'@ReplaceRegularExpression(@Value(_sign_text{1}),(?:STATE ROUTE<pipe>SR)[-\s]*,"",caseSensitive=False)'BOOL_OP;OR;COMPOSITE_TEST;1;CASE_INSENSITIVE_TEST @Value(_sign_text{1}) CONTAINS_REGEX (?:INTERSTATE<pipe>I)[-\s]*'@ReplaceRegularExpression(@Value(_sign_text{1}),(?:INTERSTATE<pipe>I)[-\s]*,"",caseSensitive=False)'FME_NUM_CONDITIONS3___
      SET_TO _direction_full (varchar(200)) = FME_CONDITIONAL:DEFAULT_VALUE'@FullTitleCase(@Value(_sign_text{0}))'BOOL_OP;OR;COMPOSITE_TEST;1;CASE_INSENSITIVE_TEST @Value(_sign_text{0}) CONTAINS_REGEX (\s*<pipe>^)\bN\b(\s*<pipe>$)'@ReplaceRegularExpression(@Value(_sign_text{0}),(\s*<pipe>^)\bN\b(\s*<pipe>$),"North",caseSensitive=False)'BOOL_OP;OR;COMPOSITE_TEST;1;CASE_INSENSITIVE_TEST @Value(_sign_text{0}) CONTAINS_REGEX (\s*<pipe>^)\bS\b(\s*<pipe>$)'@ReplaceRegularExpression(@Value(_sign_text{0}),(\s*<pipe>^)\bS\b(\s*<pipe>$),"South",caseSensitive=False)'BOOL_OP;OR;COMPOSITE_TEST;1;CASE_INSENSITIVE_TEST @Value(_sign_text{0}) CONTAINS_REGEX (\s*<pipe>^)\bE\b(\s*<pipe>$)'@ReplaceRegularExpression(@Value(_sign_text{0}),(\s*<pipe>^)\bE\b(\s*<pipe>$),"East",caseSensitive=False)'BOOL_OP;OR;COMPOSITE_TEST;1;CASE_INSENSITIVE_TEST @Value(_sign_text{0}) CONTAINS_REGEX (\s*<pipe>^)\bW\b(\s*<pipe>$)'@ReplaceRegularExpression(@Value(_sign_text{0}),(\s*<pipe>^)\bW\b(\s*<pipe>$),"West",caseSensitive=False)'FME_NUM_CONDITIONS5___
      SET_TO _direction_abbr (varchar(200)) = FME_CONDITIONAL:DEFAULT_VALUE'@FullTitleCase(@Value(_sign_text{0}))'BOOL_OP;OR;COMPOSITE_TEST;1;CASE_INSENSITIVE_TEST @Value(_sign_text{0}) CONTAINS_REGEX (\s*<pipe>^)\bNorth\b(\s*<pipe>$)'@ReplaceRegularExpression(@Value(_sign_text{0}),(\s*<pipe>^)\bNorth\b(\s*<pipe>$),"N",caseSensitive=False)'BOOL_OP;OR;COMPOSITE_TEST;1;CASE_INSENSITIVE_TEST @Value(_sign_text{0}) CONTAINS_REGEX (\s*<pipe>^)\bSouth\b(\s*<pipe>$)'@ReplaceRegularExpression(@Value(_sign_text{0}),(\s*<pipe>^)\bSouth\b(\s*<pipe>$),"S",caseSensitive=False)'BOOL_OP;OR;COMPOSITE_TEST;1;CASE_INSENSITIVE_TEST @Value(_sign_text{0}) CONTAINS_REGEX (\s*<pipe>^)\bEast\b(\s*<pipe>$)'@ReplaceRegularExpression(@Value(_sign_text{0}),(\s*<pipe>^)\bEast\b(\s*<pipe>$),"E",caseSensitive=False)'BOOL_OP;OR;COMPOSITE_TEST;1;CASE_INSENSITIVE_TEST @Value(_sign_text{0}) CONTAINS_REGEX (\s*<pipe>^)\bWest\b(\s*<pipe>$)'@ReplaceRegularExpression(@Value(_sign_text{0}),(\s*<pipe>^)\bWest\b(\s*<pipe>$),"W",caseSensitive=False)'FME_NUM_CONDITIONS5___
      SET_TO _sign_text{0} (varchar(200)) = FME_CONDITIONAL:DEFAULT_VALUE'@Value(_sign_text{0})'BOOL_OP;OR;COMPOSITE_TEST;1;CASE_INSENSITIVE_TEST @Value(_sign_text{0}) CONTAINS_REGEX \bNORTH\b'@ReplaceRegularExpression(@Value(_sign_text{0}),\bNORTH\b,"N",caseSensitive=False)'BOOL_OP;OR;COMPOSITE_TEST;1;CASE_INSENSITIVE_TEST @Value(_sign_text{0}) CONTAINS_REGEX \bSOUTH\b'@ReplaceRegularExpression(@Value(_sign_text{0}),\bSOUTH\b,"S",caseSensitive=False)'BOOL_OP;OR;COMPOSITE_TEST;1;CASE_INSENSITIVE_TEST @Value(_sign_text{0}) CONTAINS_REGEX \bEAST\b'@ReplaceRegularExpression(@Value(_sign_text{0}),\bEAST\b,"E",caseSensitive=False)'BOOL_OP;OR;COMPOSITE_TEST;1;CASE_INSENSITIVE_TEST @Value(_sign_text{0}) CONTAINS_REGEX \bWEST\b'@ReplaceRegularExpression(@Value(_sign_text{0}),\bWEST\b,"W",caseSensitive=False)'FME_NUM_CONDITIONS5___
      SET_TO _sign_text{1} (varchar(200)) = FME_CONDITIONAL:DEFAULT_VALUE'@Value(_sign_text{1})'BOOL_OP;OR;COMPOSITE_TEST;1;CASE_INSENSITIVE_TEST @Value(_sign_text{1}) CONTAINS_REGEX \bNORTH\b'@ReplaceRegularExpression(@Value(_sign_text{1}),\bNORTH\b,"N",caseSensitive=False)'BOOL_OP;OR;COMPOSITE_TEST;1;CASE_INSENSITIVE_TEST @Value(_sign_text{1}) CONTAINS_REGEX \bSOUTH\b'@ReplaceRegularExpression(@Value(_sign_text{1}),\bSOUTH\b,"S",caseSensitive=False)'BOOL_OP;OR;COMPOSITE_TEST;1;CASE_INSENSITIVE_TEST @Value(_sign_text{1}) CONTAINS_REGEX \bEAST\b'@ReplaceRegularExpression(@Value(_sign_text{1}),\bEAST\b,"E",caseSensitive=False)'BOOL_OP;OR;COMPOSITE_TEST;1;CASE_INSENSITIVE_TEST @Value(_sign_text{1}) CONTAINS_REGEX \bWEST\b'@ReplaceRegularExpression(@Value(_sign_text{1}),\bWEST\b,"W",caseSensitive=False)'FME_NUM_CONDITIONS5___
      SET_TO _sign_text_ext{0} (varchar(200)) = FME_CONDITIONAL:DEFAULT_VALUE'@Value(_sign_text_ext{0})'BOOL_OP;OR;COMPOSITE_TEST;1;CASE_INSENSITIVE_TEST @Value(_sign_text_ext{0}) CONTAINS_REGEX \bNORTH\b'@ReplaceRegularExpression(@Value(_sign_text_ext{0}),\bNORTH\b,"N",caseSensitive=False)'BOOL_OP;OR;COMPOSITE_TEST;1;CASE_INSENSITIVE_TEST @Value(_sign_text_ext{0}) CONTAINS_REGEX \bSOUTH\b'@ReplaceRegularExpression(@Value(_sign_text_ext{0}),\bSOUTH\b,"S",caseSensitive=False)'BOOL_OP;OR;COMPOSITE_TEST;1;CASE_INSENSITIVE_TEST @Value(_sign_text_ext{0}) CONTAINS_REGEX \bEAST\b'@ReplaceRegularExpression(@Value(_sign_text_ext{0}),\bEAST\b,"E",caseSensitive=False)'BOOL_OP;OR;COMPOSITE_TEST;1;CASE_INSENSITIVE_TEST @Value(_sign_text_ext{0}) CONTAINS_REGEX \bWEST\b'@ReplaceRegularExpression(@Value(_sign_text_ext{0}),\bWEST\b,"W",caseSensitive=False)'FME_NUM_CONDITIONS5___
      SET_TO _sign_text_ext{1} (varchar(200)) = FME_CONDITIONAL:DEFAULT_VALUE'@Value(_sign_text_ext{1})'BOOL_OP;OR;COMPOSITE_TEST;1;CASE_INSENSITIVE_TEST @Value(_sign_text_ext{1}) CONTAINS_REGEX \bNORTH\b'@ReplaceRegularExpression(@Value(_sign_text_ext{1}),\bNORTH\b,"N",caseSensitive=False)'BOOL_OP;OR;COMPOSITE_TEST;1;CASE_INSENSITIVE_TEST @Value(_sign_text_ext{1}) CONTAINS_REGEX \bSOUTH\b'@ReplaceRegularExpression(@Value(_sign_text_ext{1}),\bSOUTH\b,"S",caseSensitive=False)'BOOL_OP;OR;COMPOSITE_TEST;1;CASE_INSENSITIVE_TEST @Value(_sign_text_ext{1}) CONTAINS_REGEX \bEAST\b'@ReplaceRegularExpression(@Value(_sign_text_ext{1}),\bEAST\b,"E",caseSensitive=False)'BOOL_OP;OR;COMPOSITE_TEST;1;CASE_INSENSITIVE_TEST @Value(_sign_text_ext{1}) CONTAINS_REGEX \bWEST\b'@ReplaceRegularExpression(@Value(_sign_text_ext{1}),\bWEST\b,"W",caseSensitive=False)'FME_NUM_CONDITIONS5___
      SET_TO _marker_pt1 (varchar(200)) = @Value(_sign_text_ext{0})
      SET_TO _marker_pt2 (varchar(200)) = @Value(_sign_text_ext{1})
    INPUT_PORT_CONNECTED = CONNECTED
    -> if_error_2
if_error_2: Tester
    BOOL_OP = OR
    TEST_CLAUSE = TEST @Value(_primname) NOT_= ERROR
    TEST_MODE = TEST
    PASSED -> AttributeManager_2
    FAILED -> Junction
AttributeManager_2
    ATTR_TABLE:
      SET_TO DiscrpAgID (varchar(22)) = slbytnec1.shelby.tn.us
      SET_TO DateUpdate (datetime) = @CurrentDateTime()
      SET_TO NGUID (varchar(254)) = @Value(_sign_text{0})-@Value(_sign_text{1})-@Value(_sign_text_ext{0})-@Value(_sign_text_ext{1})
      SET_TO DM_Unit (varchar(15)) = Mile
      SET_TO DM_Value (number(9,3)) = FME_CONDITIONAL:DEFAULT_VALUE'@Value(_marker_pt1).@Value(_marker_pt2)'BOOL_OP;OR;COMPOSITE_TEST;1;CASE_SENSITIVE_TEST @Value(_marker_pt1) CONTAINS_REGEX [a-zA-Z]'FME_NULL_VALUE'FME_NUM_CONDITIONS2___
      SET_TO DM_Rte (varchar(100)) = @Value(_primname) @Value(_direction_full)
      SET_TO DM_Type (varchar(50)) = Road
      SET_TO DM_Ind (varchar(1)) = P
      SET_TO DM_Label (varchar(100)) = @Value(DM_Rte) Mile @Value(_sign_text_ext{0}).@Value(_sign_text_ext{1})
      SET_TO Area (varchar(100)) = @FullTitleCase(@Value(CITY))
      REMOVE COMMENTS (varchar(254))
      REMOVE MUTCD (varchar(25))
      REMOVE _sign_text{} (varchar(200))
      REMOVE _sign_text_ext{} (varchar(200))
      REMOVE _element_count (uint64)
      REMOVE CITY (varchar(100))
      REMOVE LOG_MILE (real64)
    -> if_alphanumeric
Note: Check for nulls in DM_Value. Alphanumeric combinations are written as null to not break the numeric format
if_alphanumeric: Tester
    BOOL_OP = OR
    TEST_CLAUSE = CASE_SENSITIVE_TEST DM_Value NOT_ATTRIBUTE_VALUE_NULL ""
    TEST_MODE = CASE_SENSITIVE_TEST
    PASSED -> DuplicateFilter
    FAILED -> Alphanumeric_Markers
Note: See readme on github. Dynamically assigns 00 for strings to enforce numeric schema requirements
Alphanumeric_Markers: Alphanumeric Markers
    DM_VALUE = @Value(DM_Value)
    _MARKER_PT1 = @Value(_marker_pt1)
    _MARKER_PT2 = @Value(_marker_pt2)
    -> DuplicateFilter
Note: We require unique records. Filter out duplicates (likely typos or data errors at the source)
DuplicateFilter
    INPUT_ORDERED_CHOICE_LOOKUP = NO
    KEYATTR = NGUID
    INPUT_ORDERED_CHOICE = No
    UNIQUE -> AttributeRemover_4
    UNIQUE -> alt_names_attrs_mngr
    UNIQUE -> alt_names_attrs_mngr_5
Note: how about alphanumeric for alt names?
AttributeRemover_4
    REMOVE_ATTRS = _altname1,_primname,_direction_abbr,_direction_full,_marker_pt1,_marker_pt2,_altname0,_altname2,_altname3
    -> DistanceMarkers (writer SAFE.ESRI-AGOL.ARCGISFEATURESERVICE_3)
Note: POI spelling variations: / Interstate 40W MM 4.2 / Interstate 40W Mile 4.2 / Interstate 40W MP 4.2 / Interstate 40W 4.2 / Interstate 40 West MM 4.2 / Interstate 40 West Mile 4.2 / Interstate 40 West MP 4.2 / Interstate 40 West 4.2 / Interstate 40 W MM 4.2 / Interstate 40 W Mile 4.2 / Interstate 40 W MP 4.2 / Interstate 40 W 4.2 / I-40W MM 4.2 / I-40W Mile 4.2 / I-40W MP 4.2 / I-40W 4.2 / I-40 West MM 4.2 / I-40 West Mile 4.2 / I-40 West MP 4.2 / I-40 West 4.2 / I-40 W MM 4.2 / I-40 W Mile 4.2 / I-40 W MP 4.2 / I-40 W 4.2 / I 40W MM 4.2 / I 40W Mile 4.2 / I 40W MP 4.2 / I 40W 4.2 / I 40 West MM 4.2 / I 40 West Mile 4.2 / I 40 West MP 4.2 / I 40 West 4.2 / I 40 W MM 4.2 / I 40 W Mile 4.2 / I 40 W MP 4.2 / I 40 W 4.2 / I40W MM 4.2 / I40W Mile 4.2 / I40W MP 4.2 / I40W 4.2 / I40 West MM 4.2 / I40 West Mile 4.2 / I40 West MP 4.2 / I40 West 4.2 / I40 W MM 4.2 / I40 W Mile 4.2 / I40 W MP 4.2 / I40 W 4.2 / 40W MM 4.2 / 40W Mile 4.2 / 40W MP 4.2 / 40W 4.2 / 40 West MM 4.2 / 40 West Mile 4.2 / 40 West MP 4.2 / 40 West 4.2 / 40 W MM 4.2 / 40 W Mile 4.2 / 40 W MP 4.2 / 40 W 4.2
Note: STREET NAME spelling variations: / Interstate 40 West (default) / Interstate 40 W / I40 West / I40 W / I-40 West / I-40 W / I 40 West / I 40 W
Junction_3
    -> DistanceMarker_AltNames (writer SAFE.ESRI-AGOL.ARCGISFEATURESERVICE_1)
Note: PENDING error reporting
Junction
Note: Note: These are too inconsistent to map without a lot of exceptions. Skipping for now
Junction_2
USACE_River_Mile_Markers: GET from REST
    TARGET_URL = https://services7.arcgis.com/n1YM8pTrFmm7L4hs/arcgis/rest/services/usace_river_mile_markers/FeatureServer/0
    WHERE_QUERY = RIVER_NUMB=21
    -> expose_attrs_3
USACE_Clipper: Clipper
    ADD_NODATA = YES
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> expose_attrs_7
    OUTSIDE -> expose_attrs_7
Note: Need some elements computed prior to the upcoming attr mngr
pre-comute_elements_2: AttributeCreator
    ATTR_TABLE:
      SET_TO DM_Value (number(9,3)) = @Value(name)
      SET_TO _primname (varchar(100)) = Mississippi
      SET_TO _altname0 (varchar(100)) = MS
      SET_TO _altname1 (varchar(100)) = Miss
    INPUT_PORT_CONNECTED = CONNECTED
    -> AttributeManager_4
AttributeManager_4
    ATTR_TABLE:
      SET_TO DiscrpAgID (varchar(100)) = slbytnec1.shelby.tn.us
      SET_TO DateUpdate (datetime) = @CurrentDateTime()
      SET_TO NGUID (varchar(254)) = @UpperCase(@Value(_primname)-@Value(DM_Value))
      SET_TO DM_Unit (varchar(15)) = Mile
      SET_TO DM_Type (varchar(50)) = River
      SET_TO DM_Rte (varchar(100)) = @Value(_primname)
      SET_TO DM_Ind (varchar(1)) = L
      SET_TO DM_Label (varchar(100)) = @Value(_primname) River Mile @Value(DM_Value)
      SET_TO Area (varchar(100)) = @FullTitleCase(@Value(CITY))
      REMOVE name (varchar(254))
      REMOVE CITY (varchar(100))
      REMOVE _clipped (char(3))
    -> DuplicateFilter_3
    -> AttributeRemover_12
DuplicateFilter_3
    INPUT_ORDERED_CHOICE_LOOKUP = NO
    KEYATTR = NGUID
    INPUT_ORDERED_CHOICE = No
    UNIQUE -> alt_names_attrs_mngr_3
    UNIQUE -> alt_names_attrs_mngr_6
Note: Spelling variations: / Mississippi River MM 732 / Mississippi River Mile 732 / Mississippi River 732 / Mississippi MM 732 / Mississippi Mile 732 / Mississippi 732 / MS River MM 732 / MS River Mile 732 / MS River 732 / MS MM 732 / MS Mile 732 / MS 732 / Miss River MM 732 / Miss River Mile 732 / Miss River 732 / Miss MM 732 / Miss Mile 732 / Miss 732 / MSRiver MM 732 / MSRiver Mile 732 / MSRiver 732 / MSR MM 732 / MSR Mile 732 / MSR 732
Note: Spelling variations: / Mississippi River (default - not on this stream) / Mississippi / MS / MS River / Miss / Miss River
Junction_4
    -> DistanceMarker_AltNames (writer SAFE.ESRI-AGOL.ARCGISFEATURESERVICE_1)
AttributeRemover_12
    REMOVE_ATTRS = _primname,_altname0,_altname1
    -> DistanceMarkers (writer SAFE.ESRI-AGOL.ARCGISFEATURESERVICE_3)
SC911_Trail_Markers: GET from REST
    TARGET_URL = https://services6.arcgis.com/FStub7HlCSCdqoXK/arcgis/rest/services/911_Trail_Markers/FeatureServer/0
    WHERE_QUERY = 1=1
    -> expose_attrs_4
trail_markers_clipper: Clipper
    ADD_NODATA = YES
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> expose_attrs_8
    OUTSIDE -> expose_attrs_8
Note: Need some elements computed prior to the upcoming attr mngr
pre-comute_elements_3: AttributeCreator
    ATTR_TABLE:
      SET_TO DM_Value (number(9,3)) = @Value(SIGN)
      SET_TO _primname (varchar(200)) = @Value(TRAIL)
      SET_TO _altname0 (varchar(200)) = @ReplaceRegularExpression(@Value(LABEL),\s*\d+(?:\.\d+)?[a-zA-Z]?\s*,"",caseSensitive=False)
    INPUT_PORT_CONNECTED = CONNECTED
    -> replace_.
replace_.: StringReplacer
    CASE = NO
    NO_MATCH = _FME_NO_OP_
    REGEXP = NO
    STR_REPLACE_TABLE = "_altname0 . "
    -> AttributeManager_5
AttributeManager_5
    ATTR_TABLE:
      SET_TO DiscrpAgID (varchar(100)) = slbytnec1.shelby.tn.us
      SET_TO DateUpdate (datetime) = @CurrentDateTime()
      SET_TO NGUID (varchar(254)) = @Value(SIGN)
      SET_TO DM_Unit (varchar(15)) = Unknown
      SET_TO DM_Rte (varchar(100)) = @Value(_primname)
      SET_TO DM_Type (varchar(50)) = Trail
      SET_TO DM_Ind (varchar(1)) = P
      SET_TO DM_Label (varchar(100)) = @Value(_primname) @Value(SIGN)
      SET_TO Area (varchar(100)) = @FullTitleCase(@Value(CITY))
      REMOVE SIGN (varchar(254))
      REMOVE TRAIL (varchar(200))
      REMOVE NAME (varchar(200))
      REMOVE LABEL (varchar(200))
      REMOVE CITY (varchar(100))
    USER_EXPOSED_ATTRIBUTES = name,_clipped
    -> DuplicateFilter_2
DuplicateFilter_2
    INPUT_ORDERED_CHOICE_LOOKUP = NO
    KEYATTR = NGUID
    INPUT_ORDERED_CHOICE = No
    UNIQUE -> alt_names_attrs_mngr_4
    UNIQUE -> alt_names_attrs_mngr_7
Note: Spelling variations: / Germantown Greenway Trail Marker 224 / Germantown Greenway Trail 224 / Germantown Greenway Marker 224 / Germantown Greenway 224 / GG Trail Marker 224 / GG Trail 224 / GG Marker 224 / GG 224 / GG224 / Trail Marker 224 Germantown Greenway / Trail 224 Germantown Greenway / Marker 224 Germantown Greenway / 224 Germantown Greenway / Trail Marker 224 GG / Trail 224 GG / Marker 224 GG / 224 GG / Trail Marker 224GG / Trail 224GG / Marker 224GG / 224GG
Note: Spelling variations: / Germantown Greenway (default - not included in this stream) / Germantown Greenway Trail / GG / GG Trail
Junction_5
    -> TrailMarker_AltNames (writer SAFE.ESRI-AGOL.ARCGISFEATURESERVICE_2)
FRA_Rail_Posts: GET from REST
    TARGET_URL = https://services.arcgis.com/xOi1kZaI0eWDREZv/arcgis/rest/services/NTAD_Rail_Mileposts/FeatureServer/0/
    WHERE_QUERY = STCYFIPS=47157
    -> expose_attrs_2
FRA_ESZ_clipper: Clipper
    ADD_NODATA = YES
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> expose_attrs_6
    OUTSIDE -> expose_attrs_6
FRA_Rail_Lines: GET from REST
    TARGET_URL = https://services.arcgis.com/xOi1kZaI0eWDREZv/arcgis/rest/services/NTAD_North_American_Rail_Network_Lines/FeatureServer/0
    WHERE_QUERY = STCNTYFIPS=47157
    -> expose_attrs_9
Bufferer_2
    ANGLE = 22.5
    CAP_STYLE_LOOKUP = CAP_ROUND
    CORNER_STYLE_LOOKUP = JOIN_ARC
    MODE = AREA
    OFFSET = 5
    OFFSET_UNITS = FEET
    PRECISION = APPROX
    CAP_STYLE = Round
    CORNER_STYLE = Arc
    BUFFERED -> FRA_ESZ_clipper_2 [CLIPPER]
FRA_ESZ_clipper_2: Clipper
    ADD_NODATA = YES
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> pre-comute_elements
Note: Need some elements computed prior to the upcoming attr mngr
pre-comute_elements: AttributeCreator
    ATTR_TABLE:
      SET_TO DM_Value (number(9,3)) = @Value(MILEPOST)
      SET_TO _primname (varchar(200)) = FME_CONDITIONAL:DEFAULT_VALUE'ERROR'BOOL_OP;OR;COMPOSITE_TEST;1;TEST @Value(RROWNER1) = BNSF'BNSF Railway'BOOL_OP;OR;COMPOSITE_TEST;1;TEST @Value(RROWNER1) = CN'Canadian National Railway'BOOL_OP;OR;COMPOSITE_TEST;1;TEST @Value(RROWNER1) = CSXT'CSX Transportation'BOOL_OP;OR;COMPOSITE_TEST;1;TEST @Value(RROWNER1) = GRYR'Grenada Railway'BOOL_OP;OR;COMPOSITE_TEST;1;TEST @Value(RROWNER1) = MSCI'Mississippi Central Railroad'BOOL_OP;OR;COMPOSITE_TEST;1;TEST @Value(RROWNER1) = NS'Norfolk Southern Railway'BOOL_OP;OR;COMPOSITE_TEST;1;TEST @Value(RROWNER1) = RJCK'R J Corman Railroad'BOOL_OP;OR;COMPOSITE_TEST;1;TEST @Value(RROWNER1) = UP'Union Pacific Railroad'BOOL_OP;OR;COMPOSITE_TEST;1;TEST @Value(RROWNER1) = WMBR'West Memphis Base Railroad'FME_NUM_CONDITIONS10___
      SET_TO _altname0 (varchar(200)) = @Value(RROWNER1)
    INPUT_PORT_CONNECTED = CONNECTED
    -> AttributeManager_3
AttributeManager_3
    ATTR_TABLE:
      SET_TO DiscrpAgID (varchar(100)) = slbytnec1.shelby.tn.us
      SET_TO DateUpdate (datetime) = @CurrentDateTime()
      SET_TO NGUID (varchar(254)) = @UpperCase(@Value(RROWNER1)-@Value(DM_Value))
      SET_TO DM_Unit (varchar(15)) = Mile
      SET_TO DM_Rte (varchar(100)) = @Value(_primname)
      SET_TO DM_Type (varchar(50)) = Railroad
      SET_TO DM_Ind (varchar(1)) = P
      SET_TO DM_Label (varchar(100)) = @Value(_primname) Milepost @Value(MILEPOST)
      SET_TO Area (varchar(100)) = @FullTitleCase(@Value(CITY))
      REMOVE MILEPOST (number(9,3))
      REMOVE CITY (varchar(100))
      REMOVE RROWNER1 (varchar(100))
      REMOVE _clipped (char(3))
    -> DuplicateFilter_4
    -> AttributeRemover_10
DuplicateFilter_4
    INPUT_ORDERED_CHOICE_LOOKUP = NO
    KEYATTR = NGUID
    INPUT_ORDERED_CHOICE = No
    UNIQUE -> alt_names_attrs_mngr_2
    UNIQUE -> alt_names_attrs_mngr_8
Note: Spelling variations: / Canadian National Railway Mile Marker 378 / Canadian National Railway MM 378 / Canadian National Railway Marker 378 / Canadian National Railway Milepost 378 / Canadian National Railway MP 378 / Canadian National Railway Post 378 / Canadian National Railway Mile 378 / Canadian National Railway 378 / CN Mile Marker 378 / CN MM 378 / CN Marker 378 / CN Milepost 378 / CN MP 378 / CN Post 378 / CN Mile 378 / CN 378 / Mile Marker 378 Canadian National Railway / MM 378 Canadian National Railway / Marker 378 Canadian National Railway / Milepost 378 Canadian National Railway / MP 378 Canadian National Railway / Post 378 Canadian National Railway / Mile 378 Canadian National Railway / 378 Canadian National Railway / Mile Marker 378 CN / MM 378 CN / Marker 378 CN / Milepost 378 CN / MP 378 CN / Post 378 CN / Mile 378 CN / 378 CN
Note: Spelling variations: / Canadian National Railway (default - not on this stream) / CN
Junction_6
    -> DistanceMarker_AltNames (writer SAFE.ESRI-AGOL.ARCGISFEATURESERVICE_1)
AttributeRemover_10
    REMOVE_ATTRS = _primname,_altname0
    -> DistanceMarkers (writer SAFE.ESRI-AGOL.ARCGISFEATURESERVICE_3)

Bookmark: Clip against boundary
Note: Note: this one only clips. No attribute accumulation like the clipper upstream
HullAccumulator
    3DMODETYPE = MAKE2D
    ACCUM_INPUT_ATTRS_LOOKUP = One
    HULLTYPE = CONVEX
    3DMODE_PARAM = 2D
    ACCUM_INPUT_ATTRS = Use Attributes From One Feature
    HULLTYPE_PARAM = Convex ()
    HULL -> Bufferer
Bufferer
    ANGLE = 22.5
    CAP_STYLE_LOOKUP = CAP_ARC
    CORNER_STYLE_LOOKUP = JOIN_ARC
    MODE = AREA
    OFFSET = 5
    OFFSET_UNITS = MILES
    PRECISION = APPROX
    CAP_STYLE = Arc
    CORNER_STYLE = Arc
    BUFFERED -> USACE_Clipper_2 [CLIPPER]
USACE_Clipper_2: Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> pre-comute_elements_2

Bookmark: Clean up TDOT fields
expose_attrs: AttributeExposer
    ATTR_TABLE = COMMENTS,varchar(254),MUTCD,varchar(25),LOG_MILE,real64
    -> AttributeRemover
AttributeRemover
    REMOVE_ATTRS = _copynum,_count,_http_status_code,_offset,_page_size,_pages,_response_body,json_index,json_type
    -> filter_results

Bookmark: Clean up TDOT fields
expose_attrs_5: AttributeExposer
    ATTR_TABLE = CITY,varchar(100)
    -> AttributeRemover_6
AttributeRemover_6
    REMOVE_ATTRS = _copynum,_count,_http_status_code,_offset,_page_size,_pages,_response_body,json_index,json_type,_clipped
    -> remove_unnecessary

Bookmark: Create alt names table - alt street name
Note: Create alt name fields in a list
alt_names_attrs_mngr: AttributeManager
    ATTR_TABLE:
      RENAME_SET_VALUE NGUID > nguid (varchar(254))
      SET_TO joinrole (varchar(50)) = AlternateStreetName
      SET_TO joinfor (varchar(50)) = Highway
      SET_TO _altnames{0}.name (varchar(200)) = @Value(_primname) @Value(_direction_abbr)
      SET_TO _altnames{1}.name (varchar(200)) = @Value(_altname0) @Value(_direction_full)
      SET_TO _altnames{2}.name (varchar(200)) = @Value(_altname0) @Value(_direction_abbr)
      SET_TO _altnames{3}.name (varchar(200)) = @Value(_altname1) @Value(_direction_full)
      SET_TO _altnames{4}.name (varchar(200)) = @Value(_altname1) @Value(_direction_abbr)
      SET_TO _altnames{5}.name (varchar(200)) = @Value(_altname2) @Value(_direction_full)
      SET_TO _altnames{6}.name (varchar(200)) = @Value(_altname2) @Value(_direction_abbr)
      REMOVE DiscrpAgID (varchar(100))
      REMOVE DateUpdate (datetime)
      REMOVE DM_Unit (varchar(15))
      REMOVE DM_Value (number(9,3))
      REMOVE DM_Rte (varchar(100))
      REMOVE DM_Type (varchar(50))
      REMOVE DM_Ind (varchar(1))
      REMOVE DM_Label (varchar(100))
      REMOVE _primname (varchar(100))
      REMOVE _altname1 (varchar(200))
      REMOVE _direction_full (varchar(200))
      REMOVE _direction_abbr (varchar(200))
      REMOVE Area (varchar(100))
      REMOVE _marker_pt1 (varchar(200))
      REMOVE _marker_pt2 (varchar(200))
      REMOVE _altname0 (varchar(200))
      REMOVE _altname2 (varchar(200))
      REMOVE _altname3 (varchar(200))
    -> ListExploder
Note: Explode the list (turn list into rows). Important to note that we're keeping the ShelbyID attribute because that's a requirement for the locator alt name join
ListExploder
    ATTR_CONFLICT_RES_LOOKUP = INCOMING_IF_CONFLICT
    INDEX_ATTR = _element_index
    LIST_ATTR = _altnames{}
    ATTR_ACCUM_MODE = Merge List Attributes
    ATTR_CONFLICT_RES = Use List Attribute Values
    ELEMENTS -> remove_geometry
remove_geometry: GeometryRemover
    GEOM_NAME_SELECTION = FME_ALL_GEOMETRIES
    REMOVE_COORDSYS = Yes
    -> clean_up_fields
clean_up_fields: AttributeRemover
    REMOVE_ATTRS = _element_index
    -> Junction_3

Bookmark: Create alt names table - alt poi name
alt_names_attrs_mngr_5: AttributeManager
    ATTR_TABLE:
      RENAME_SET_VALUE NGUID > nguid (varchar(254))
      SET_TO joinrole (varchar(50)) = AlternatePOIName
      SET_TO joinfor (varchar(50)) = Highway
      SET_TO _altnames{0}.name (varchar(200)) = @Value(_primname)@Value(_direction_abbr) MM @Value(DM_Value)
      SET_TO _altnames{1}.name (varchar(200)) = @Value(_primname)@Value(_direction_abbr) Mile @Value(DM_Value)
      SET_TO _altnames{2}.name (varchar(200)) = @Value(_primname)@Value(_direction_abbr) MP @Value(DM_Value)
      SET_TO _altnames{3}.name (varchar(200)) = @Value(_primname)@Value(_direction_abbr) @Value(DM_Value)
      SET_TO _altnames{4}.name (varchar(200)) = @Value(_primname) @Value(_direction_full) MM @Value(DM_Value)
      SET_TO _altnames{5}.name (varchar(200)) = @Value(_primname) @Value(_direction_full) Mile @Value(DM_Value)
      SET_TO _altnames{6}.name (varchar(200)) = @Value(_primname) @Value(_direction_full) MP @Value(DM_Value)
      SET_TO _altnames{7}.name (varchar(200)) = @Value(_primname) @Value(_direction_full) @Value(DM_Value)
      SET_TO _altnames{8}.name (varchar(200)) = @Value(_primname) @Value(_direction_abbr) MM @Value(DM_Value)
      SET_TO _altnames{9}.name (varchar(200)) = @Value(_primname) @Value(_direction_abbr) Mile @Value(DM_Value)
      SET_TO _altnames{10}.name (varchar(200)) = @Value(_primname) @Value(_direction_abbr) MP @Value(DM_Value)
      SET_TO _altnames{11}.name (varchar(200)) = @Value(_primname) @Value(_direction_abbr) @Value(DM_Value)
      REMOVE DiscrpAgID (varchar(100))
      SET_TO _altnames{12}.name (varchar(200)) = @Value(_altname0)@Value(_direction_abbr) MM @Value(DM_Value)
      SET_TO _altnames{13}.name (varchar(200)) = @Value(_altname0)@Value(_direction_abbr) Mile @Value(DM_Value)
      SET_TO _altnames{14}.name (varchar(200)) = @Value(_altname0)@Value(_direction_abbr) MP @Value(DM_Value)
      SET_TO _altnames{15}.name (varchar(200)) = @Value(_altname0)@Value(_direction_abbr) @Value(DM_Value)
      SET_TO _altnames{16}.name (varchar(200)) = @Value(_altname0) @Value(_direction_full) MM @Value(DM_Value)
      SET_TO _altnames{17}.name (varchar(200)) = @Value(_altname0) @Value(_direction_full) Mile @Value(DM_Value)
      SET_TO _altnames{18}.name (varchar(200)) = @Value(_altname0) @Value(_direction_full) MP @Value(DM_Value)
      SET_TO _altnames{19}.name (varchar(200)) = @Value(_altname0) @Value(_direction_full) @Value(DM_Value)
      SET_TO _altnames{20}.name (varchar(200)) = @Value(_altname0) @Value(_direction_abbr) MM @Value(DM_Value)
      SET_TO _altnames{21}.name (varchar(200)) = @Value(_altname0) @Value(_direction_abbr) Mile @Value(DM_Value)
      SET_TO _altnames{22}.name (varchar(200)) = @Value(_altname0) @Value(_direction_abbr) MP @Value(DM_Value)
      SET_TO _altnames{23}.name (varchar(200)) = @Value(_altname0) @Value(_direction_abbr) @Value(DM_Value)
      REMOVE DateUpdate (datetime)
      SET_TO _altnames{24}.name (varchar(200)) = @Value(_altname1)@Value(_direction_abbr) MM @Value(DM_Value)
      SET_TO _altnames{25}.name (varchar(200)) = @Value(_altname1)@Value(_direction_abbr) Mile @Value(DM_Value)
      SET_TO _altnames{26}.name (varchar(200)) = @Value(_altname1)@Value(_direction_abbr) MP @Value(DM_Value)
      SET_TO _altnames{27}.name (varchar(200)) = @Value(_altname1)@Value(_direction_abbr) @Value(DM_Value)
      SET_TO _altnames{28}.name (varchar(200)) = @Value(_altname1) @Value(_direction_full) MM @Value(DM_Value)
      SET_TO _altnames{29}.name (varchar(200)) = @Value(_altname1) @Value(_direction_full) Mile @Value(DM_Value)
      SET_TO _altnames{30}.name (varchar(200)) = @Value(_altname1) @Value(_direction_full) MP @Value(DM_Value)
      SET_TO _altnames{31}.name (varchar(200)) = @Value(_altname1) @Value(_direction_full) @Value(DM_Value)
      SET_TO _altnames{32}.name (varchar(200)) = @Value(_altname1) @Value(_direction_abbr) MM @Value(DM_Value)
      SET_TO _altnames{33}.name (varchar(200)) = @Value(_altname1) @Value(_direction_abbr) Mile @Value(DM_Value)
      SET_TO _altnames{34}.name (varchar(200)) = @Value(_altname1) @Value(_direction_abbr) MP @Value(DM_Value)
      SET_TO _altnames{35}.name (varchar(200)) = @Value(_altname1) @Value(_direction_abbr) @Value(DM_Value)
      REMOVE DM_Unit (varchar(15))
      SET_TO _altnames{36}.name (varchar(200)) = @Value(_altname2)@Value(_direction_abbr) MM @Value(DM_Value)
      SET_TO _altnames{37}.name (varchar(200)) = @Value(_altname2)@Value(_direction_abbr) Mile @Value(DM_Value)
      SET_TO _altnames{38}.name (varchar(200)) = @Value(_altname2)@Value(_direction_abbr) MP @Value(DM_Value)
      SET_TO _altnames{39}.name (varchar(200)) = @Value(_altname2)@Value(_direction_abbr) @Value(DM_Value)
      SET_TO _altnames{40}.name (varchar(200)) = @Value(_altname2) @Value(_direction_full) MM @Value(DM_Value)
      SET_TO _altnames{41}.name (varchar(200)) = @Value(_altname2) @Value(_direction_full) Mile @Value(DM_Value)
      SET_TO _altnames{42}.name (varchar(200)) = @Value(_altname2) @Value(_direction_full) MP @Value(DM_Value)
      SET_TO _altnames{43}.name (varchar(200)) = @Value(_altname2) @Value(_direction_full) @Value(DM_Value)
      SET_TO _altnames{44}.name (varchar(200)) = @Value(_altname2) @Value(_direction_abbr) MM @Value(DM_Value)
      SET_TO _altnames{45}.name (varchar(200)) = @Value(_altname2) @Value(_direction_abbr) Mile @Value(DM_Value)
      SET_TO _altnames{46}.name (varchar(200)) = @Value(_altname2) @Value(_direction_abbr) MP @Value(DM_Value)
      SET_TO _altnames{47}.name (varchar(200)) = @Value(_altname2) @Value(_direction_abbr) @Value(DM_Value)
      REMOVE DM_Rte (varchar(100))
      SET_TO _altnames{48}.name (varchar(200)) = @Value(_altname3)@Value(_direction_abbr) MM @Value(DM_Value)
      SET_TO _altnames{49}.name (varchar(200)) = @Value(_altname3)@Value(_direction_abbr) Mile @Value(DM_Value)
      SET_TO _altnames{50}.name (varchar(200)) = @Value(_altname3)@Value(_direction_abbr) MP @Value(DM_Value)
      SET_TO _altnames{51}.name (varchar(200)) = @Value(_altname3)@Value(_direction_abbr) @Value(DM_Value)
      SET_TO _altnames{52}.name (varchar(200)) = @Value(_altname3) @Value(_direction_full) MM @Value(DM_Value)
      SET_TO _altnames{53}.name (varchar(200)) = @Value(_altname3) @Value(_direction_full) Mile @Value(DM_Value)
      SET_TO _altnames{54}.name (varchar(200)) = @Value(_altname3) @Value(_direction_full) MP @Value(DM_Value)
      SET_TO _altnames{55}.name (varchar(200)) = @Value(_altname3) @Value(_direction_full) @Value(DM_Value)
      SET_TO _altnames{56}.name (varchar(200)) = @Value(_altname3) @Value(_direction_abbr) MM @Value(DM_Value)
      SET_TO _altnames{57}.name (varchar(200)) = @Value(_altname3) @Value(_direction_abbr) Mile @Value(DM_Value)
      SET_TO _altnames{58}.name (varchar(200)) = @Value(_altname3) @Value(_direction_abbr) MP @Value(DM_Value)
      SET_TO _altnames{59}.name (varchar(200)) = @Value(_altname3) @Value(_direction_abbr) @Value(DM_Value)
      REMOVE DM_Value (number(9,3))
      REMOVE DM_Type (varchar(50))
      REMOVE DM_Ind (varchar(1))
      REMOVE DM_Label (varchar(100))
      REMOVE _primname (varchar(100))
      REMOVE _altname1 (varchar(200))
      REMOVE _direction_full (varchar(200))
      REMOVE _direction_abbr (varchar(200))
      REMOVE Area (varchar(100))
      REMOVE _marker_pt1 (varchar(200))
      REMOVE _marker_pt2 (varchar(200))
      REMOVE _altname0 (varchar(200))
      REMOVE _altname2 (varchar(200))
      REMOVE _altname3 (varchar(200))
    -> ListExploder_5
ListExploder_5
    ATTR_CONFLICT_RES_LOOKUP = INCOMING_IF_CONFLICT
    INDEX_ATTR = _element_index
    LIST_ATTR = _altnames{}
    ATTR_ACCUM_MODE = Merge List Attributes
    ATTR_CONFLICT_RES = Use List Attribute Values
    ELEMENTS -> remove_geometry_5
remove_geometry_5: GeometryRemover
    GEOM_NAME_SELECTION = FME_ALL_GEOMETRIES
    REMOVE_COORDSYS = Yes
    -> clean_up_fields_5
clean_up_fields_5: AttributeRemover
    REMOVE_ATTRS = _element_index
    -> Junction_3

Bookmark: Clean up USACE fields
expose_attrs_3: AttributeExposer
    ATTR_TABLE = name,varchar(254)
    -> AttributeRemover_3
AttributeRemover_3
    REMOVE_ATTRS = _copynum,_count,_http_status_code,_offset,_page_size,_pages,_response_body,json_index,json_type
    -> USACE_Clipper [CANDIDATE]

Bookmark: Clean up USACE fields
expose_attrs_7: AttributeExposer
    ATTR_TABLE = CITY,varchar(100)
    -> AttributeRemover_8
AttributeRemover_8
    REMOVE_ATTRS = _copynum,_count,_http_status_code,_offset,_page_size,_pages,_response_body,json_index,json_type,_clipped
    -> USACE_Clipper_2 [CANDIDATE]

Bookmark: Create alt names table - alt street name
alt_names_attrs_mngr_3: AttributeManager
    ATTR_TABLE:
      RENAME_SET_VALUE NGUID > nguid (varchar(254))
      SET_TO joinrole (varchar(50)) = AlternateStreetName
      SET_TO joinfor (varchar(50)) = River
      SET_TO _altnames{0}.name (varchar(200)) = @Value(_primname)
      SET_TO _altnames{1}.name (varchar(200)) = @Value(_altname0)
      SET_TO _altnames{2}.name (varchar(200)) = @Value(_altname0) River
      SET_TO _altnames{3}.name (varchar(200)) = @Value(_altname1)
      SET_TO _altnames{4}.name (varchar(200)) = @Value(_altname1) River
      REMOVE DiscrpAgID (varchar(100))
      REMOVE DateUpdate (datetime)
      REMOVE DM_Unit (varchar(15))
      REMOVE DM_Value (number(9,3))
      REMOVE DM_Type (varchar(50))
      REMOVE DM_Ind (varchar(1))
      REMOVE DM_Label (varchar(100))
      REMOVE Area (varchar(100))
      REMOVE _primname (varchar(100))
      REMOVE _altname0 (varchar(100))
      REMOVE _altname1 (varchar(100))
      REMOVE DM_Rte (varchar(100))
    -> ListExploder_3
ListExploder_3
    ATTR_CONFLICT_RES_LOOKUP = INCOMING_IF_CONFLICT
    INDEX_ATTR = _element_index
    LIST_ATTR = _altnames{}
    ATTR_ACCUM_MODE = Merge List Attributes
    ATTR_CONFLICT_RES = Use List Attribute Values
    ELEMENTS -> remove_geometry_3
remove_geometry_3: GeometryRemover
    GEOM_NAME_SELECTION = FME_ALL_GEOMETRIES
    REMOVE_COORDSYS = Yes
    -> clean_up_fields_3
clean_up_fields_3: AttributeRemover
    REMOVE_ATTRS = _element_index,AltLabel1,AltLabel2,AltLabel3,AltLabel4,AltLabel5,AltLabel6,AltLabel7
    -> Junction_4

Bookmark: Create alt names table - alt poi name
alt_names_attrs_mngr_6: AttributeManager
    ATTR_TABLE:
      RENAME_SET_VALUE NGUID > nguid (varchar(254))
      SET_TO joinrole (varchar(50)) = AlternatePOIName
      SET_TO joinfor (varchar(50)) = River
      SET_TO _altnames{0}.name (varchar(200)) = @Value(_primname) River MM @Value(DM_Value)
      SET_TO _altnames{1}.name (varchar(200)) = @Value(_primname) River Mile @Value(DM_Value)
      SET_TO _altnames{2}.name (varchar(200)) = @Value(_primname) River @Value(DM_Value)
      SET_TO _altnames{3}.name (varchar(200)) = @Value(_primname) MM @Value(DM_Value)
      SET_TO _altnames{4}.name (varchar(200)) = @Value(_primname) Mile @Value(DM_Value)
      SET_TO _altnames{5}.name (varchar(200)) = @Value(_primname) @Value(DM_Value)
      REMOVE DiscrpAgID (varchar(100))
      SET_TO _altnames{6}.name (varchar(200)) = @Value(_altname0) River MM @Value(DM_Value)
      SET_TO _altnames{7}.name (varchar(200)) = @Value(_altname0) River Mile @Value(DM_Value)
      SET_TO _altnames{8}.name (varchar(200)) = @Value(_altname0) River @Value(DM_Value)
      SET_TO _altnames{9}.name (varchar(200)) = @Value(_altname0) MM @Value(DM_Value)
      SET_TO _altnames{10}.name (varchar(200)) = @Value(_altname0) Mile @Value(DM_Value)
      SET_TO _altnames{11}.name (varchar(200)) = @Value(_altname0) @Value(DM_Value)
      REMOVE DateUpdate (datetime)
      SET_TO _altnames{12}.name (varchar(200)) = @Value(_altname1) River MM @Value(DM_Value)
      SET_TO _altnames{13}.name (varchar(200)) = @Value(_altname1) River Mile @Value(DM_Value)
      SET_TO _altnames{14}.name (varchar(200)) = @Value(_altname1) River @Value(DM_Value)
      SET_TO _altnames{15}.name (varchar(200)) = @Value(_altname1) MM @Value(DM_Value)
      SET_TO _altnames{16}.name (varchar(200)) = @Value(_altname1) Mile @Value(DM_Value)
      SET_TO _altnames{17}.name (varchar(200)) = @Value(_altname1) @Value(DM_Value)
      REMOVE DM_Unit (varchar(15))
      SET_TO _altnames{18}.name (varchar(200)) = @Value(_altname0)River MM @Value(DM_Value)
      SET_TO _altnames{19}.name (varchar(200)) = @Value(_altname0)River Mile @Value(DM_Value)
      SET_TO _altnames{20}.name (varchar(200)) = @Value(_altname0)River @Value(DM_Value)
      SET_TO _altnames{21}.name (varchar(200)) = @Value(_altname0)R MM @Value(DM_Value)
      SET_TO _altnames{22}.name (varchar(200)) = @Value(_altname0)R Mile @Value(DM_Value)
      SET_TO _altnames{23}.name (varchar(200)) = @Value(_altname0)R @Value(DM_Value)
      REMOVE DM_Value (number(9,3))
      REMOVE DM_Type (varchar(50))
      REMOVE DM_Ind (varchar(1))
      REMOVE DM_Label (varchar(100))
      REMOVE Area (varchar(100))
      REMOVE _primname (varchar(100))
      REMOVE _altname0 (varchar(100))
      REMOVE _altname1 (varchar(100))
      REMOVE DM_Rte (varchar(100))
    -> ListExploder_6
ListExploder_6
    ATTR_CONFLICT_RES_LOOKUP = INCOMING_IF_CONFLICT
    INDEX_ATTR = _element_index
    LIST_ATTR = _altnames{}
    ATTR_ACCUM_MODE = Merge List Attributes
    ATTR_CONFLICT_RES = Use List Attribute Values
    ELEMENTS -> remove_geometry_6
remove_geometry_6: GeometryRemover
    GEOM_NAME_SELECTION = FME_ALL_GEOMETRIES
    REMOVE_COORDSYS = Yes
    -> clean_up_fields_6
clean_up_fields_6: AttributeRemover
    REMOVE_ATTRS = _element_index,AltLabel1,AltLabel2,AltLabel3,AltLabel4,AltLabel5,AltLabel6,AltLabel7
    -> Junction_4

Bookmark: Clean up trail marker fields
expose_attrs_4: AttributeExposer
    ATTR_TABLE = SIGN,varchar(254),TRAIL,,NAME,,LABEL,
    -> AttributeRemover_5
AttributeRemover_5
    REMOVE_ATTRS = _copynum,_count,_http_status_code,_offset,_page_size,_pages,_response_body,json_index,json_type
    -> trail_markers_clipper [CANDIDATE]

Bookmark: Clean up trail marker fields
expose_attrs_8: AttributeExposer
    ATTR_TABLE = CITY,varchar(100)
    -> AttributeRemover_9
AttributeRemover_9
    REMOVE_ATTRS = _copynum,_count,_http_status_code,_offset,_page_size,_pages,_response_body,json_index,json_type,_clipped
    -> pre-comute_elements_3

Bookmark: Create alt names table - alt street name
alt_names_attrs_mngr_4: AttributeManager
    ATTR_TABLE:
      RENAME_SET_VALUE NGUID > nguid (varchar(254))
      SET_TO joinrole (varchar(50)) = AlternateStreetName
      SET_TO joinfor (varchar(50)) = Trail
      SET_TO _altnames{0}.name (varchar(200)) = @Value(_primname) Trail
      SET_TO _altnames{1}.name (varchar(200)) = @Value(_altname0)
      SET_TO _altnames{2}.name (varchar(200)) = @Value(_altname0) Trail
      REMOVE _primname (varchar(200))
      REMOVE _altname0 (varchar(200))
      REMOVE DiscrpAgID (varchar(100))
      REMOVE DateUpdate (datetime)
      REMOVE DM_Unit (varchar(15))
      REMOVE DM_Value (number(9,3))
      REMOVE DM_Type (varchar(50))
      REMOVE DM_Ind (varchar(1))
      REMOVE DM_Label (varchar(100))
      REMOVE Area (varchar(100))
      REMOVE DM_Rte (varchar(100))
    -> ListExploder_4
ListExploder_4
    ATTR_CONFLICT_RES_LOOKUP = INCOMING_IF_CONFLICT
    INDEX_ATTR = _element_index
    LIST_ATTR = _altnames{}
    ATTR_ACCUM_MODE = Merge List Attributes
    ATTR_CONFLICT_RES = Use List Attribute Values
    ELEMENTS -> remove_geometry_4
remove_geometry_4: GeometryRemover
    GEOM_NAME_SELECTION = FME_ALL_GEOMETRIES
    REMOVE_COORDSYS = Yes
    -> clean_up_fields_4
clean_up_fields_4: AttributeRemover
    REMOVE_ATTRS = _element_index,AltLabel1,AltLabel2,AltLabel3,AltLabel4,AltLabel5,AltLabel6,AltLabel7
    -> Junction_5

Bookmark: Create alt names table - alt poi name
alt_names_attrs_mngr_7: AttributeManager
    ATTR_TABLE:
      RENAME_SET_VALUE NGUID > nguid (varchar(254))
      SET_TO joinrole (varchar(50)) = AlternatePOIName
      SET_TO joinfor (varchar(50)) = Trail
      SET_TO _altnames{0}.name (varchar(200)) = @Value(_primname) Trail Marker @Value(DM_Value)
      SET_TO _altnames{1}.name (varchar(200)) = @Value(_primname) Trail @Value(DM_Value)
      SET_TO _altnames{2}.name (varchar(200)) = @Value(_primname) Marker @Value(DM_Value)
      SET_TO _altnames{3}.name (varchar(200)) = @Value(_primname) @Value(DM_Value)
      SET_TO _altnames{4}.name (varchar(200)) = Trail Marker @Value(DM_Value) @Value(_primname)
      SET_TO _altnames{5}.name (varchar(200)) = Trail @Value(DM_Value) @Value(_primname)
      SET_TO _altnames{6}.name (varchar(200)) = Marker @Value(DM_Value) @Value(_primname)
      SET_TO _altnames{7}.name (varchar(200)) = @Value(DM_Value) @Value(_primname)
      REMOVE DiscrpAgID (varchar(100))
      SET_TO _altnames{8}.name (varchar(200)) = @Value(_altname0) Trail Marker @Value(DM_Value)
      SET_TO _altnames{9}.name (varchar(200)) = @Value(_altname0) Trail @Value(DM_Value)
      SET_TO _altnames{10}.name (varchar(200)) = @Value(_altname0) Marker @Value(DM_Value)
      SET_TO _altnames{11}.name (varchar(200)) = @Value(_altname0) @Value(DM_Value)
      SET_TO _altnames{12}.name (varchar(200)) = Trail Marker @Value(DM_Value) @Value(_altname0)
      SET_TO _altnames{13}.name (varchar(200)) = Trail @Value(DM_Value) @Value(_altname0)
      SET_TO _altnames{14}.name (varchar(200)) = Marker @Value(DM_Value) @Value(_altname0)
      SET_TO _altnames{15}.name (varchar(200)) = @Value(DM_Value) @Value(_altname0)
      REMOVE DM_Unit (varchar(15))
      SET_TO _altnames{16}.name (varchar(200)) = @Value(_altname0)@Value(DM_Value)
      REMOVE DateUpdate (datetime)
      SET_TO _altnames{17}.name (varchar(200)) = Trail Marker @Value(DM_Value)@Value(_altname0)
      SET_TO _altnames{18}.name (varchar(200)) = Trail @Value(DM_Value)@Value(_altname0)
      SET_TO _altnames{19}.name (varchar(200)) = Marker @Value(DM_Value)@Value(_altname0)
      SET_TO _altnames{20}.name (varchar(200)) = @Value(DM_Value)@Value(_altname0)
      REMOVE _altname0 (varchar(200))
      REMOVE _primname (varchar(200))
      REMOVE DM_Value (number(9,3))
      REMOVE DM_Type (varchar(50))
      REMOVE DM_Ind (varchar(1))
      REMOVE DM_Label (varchar(100))
      REMOVE Area (varchar(100))
      REMOVE DM_Rte (varchar(100))
    -> ListExploder_7
ListExploder_7
    ATTR_CONFLICT_RES_LOOKUP = INCOMING_IF_CONFLICT
    INDEX_ATTR = _element_index
    LIST_ATTR = _altnames{}
    ATTR_ACCUM_MODE = Merge List Attributes
    ATTR_CONFLICT_RES = Use List Attribute Values
    ELEMENTS -> remove_geometry_7
remove_geometry_7: GeometryRemover
    GEOM_NAME_SELECTION = FME_ALL_GEOMETRIES
    REMOVE_COORDSYS = Yes
    -> clean_up_fields_7
clean_up_fields_7: AttributeRemover
    REMOVE_ATTRS = _element_index,AltLabel1,AltLabel2,AltLabel3,AltLabel4,AltLabel5,AltLabel6,AltLabel7
    -> Junction_5

Bookmark: Writers - ArcGIS Portal
TrailMarker_AltNames (writer SAFE.ESRI-AGOL.ARCGISFEATURESERVICE_2)
    attributes: nguid String(254), joinrole String(50), joinfor String(50), name String(200)
DistanceMarker_AltNames (writer SAFE.ESRI-AGOL.ARCGISFEATURESERVICE_1)
    attributes: nguid String(254), joinrole String(50), joinfor String(50), name String(200)

Bookmark: Clean up FRA fields
expose_attrs_2: AttributeExposer
    ATTR_TABLE = MILEPOST,number(9,3)
    -> AttributeRemover_2
AttributeRemover_2
    REMOVE_ATTRS = _copynum,_count,_http_status_code,_offset,_page_size,_pages,_response_body,json_index,json_type
    -> FRA_ESZ_clipper [CANDIDATE]

Bookmark: Clean up FRA fields
expose_attrs_6: AttributeExposer
    ATTR_TABLE = CITY,varchar(100)
    -> AttributeRemover_7
AttributeRemover_7
    REMOVE_ATTRS = _copynum,_count,_http_status_code,_offset,_page_size,_pages,_response_body,json_index,json_type,_clipped
    -> FRA_ESZ_clipper_2 [CANDIDATE]

Bookmark: Clean up FRA fields
expose_attrs_9: AttributeExposer
    ATTR_TABLE = RROWNER1,varchar(100)
    -> AttributeRemover_11
AttributeRemover_11
    REMOVE_ATTRS = _copynum,_count,_http_status_code,_offset,_page_size,_pages,_response_body,json_index,json_type
    -> Bufferer_2

Bookmark: Create alt names table - alt street name
alt_names_attrs_mngr_2: AttributeManager
    ATTR_TABLE:
      RENAME_SET_VALUE NGUID > nguid (varchar(254))
      SET_TO joinrole (varchar(50)) = AlternateStreetName
      SET_TO joinfor (varchar(50)) = Railroad
      SET_TO _altnames{0}.name (varchar(200)) = @Value(_altname0)
      REMOVE DiscrpAgID (varchar(100))
      REMOVE DateUpdate (datetime)
      REMOVE DM_Unit (varchar(15))
      REMOVE DM_Value (number(9,3))
      REMOVE DM_Type (varchar(50))
      REMOVE DM_Ind (varchar(1))
      REMOVE DM_Label (varchar(100))
      REMOVE Area (varchar(100))
      REMOVE _primname (varchar(200))
      REMOVE _altname0 (varchar(200))
      REMOVE DM_Rte (varchar(100))
    -> ListExploder_2
ListExploder_2
    ATTR_CONFLICT_RES_LOOKUP = INCOMING_IF_CONFLICT
    INDEX_ATTR = _element_index
    LIST_ATTR = _altnames{}
    ATTR_ACCUM_MODE = Merge List Attributes
    ATTR_CONFLICT_RES = Use List Attribute Values
    ELEMENTS -> remove_geometry_2
remove_geometry_2: GeometryRemover
    GEOM_NAME_SELECTION = FME_ALL_GEOMETRIES
    REMOVE_COORDSYS = Yes
    -> clean_up_fields_2
clean_up_fields_2: AttributeRemover
    REMOVE_ATTRS = _element_index,AltLabel1,AltLabel2,AltLabel3,AltLabel4,AltLabel5,AltLabel6,AltLabel7
    -> Junction_6

Bookmark: Create alt names table - alt poi name
alt_names_attrs_mngr_8: AttributeManager
    ATTR_TABLE:
      RENAME_SET_VALUE NGUID > nguid (varchar(254))
      SET_TO joinrole (varchar(50)) = AlternatePOIName
      SET_TO joinfor (varchar(50)) = Railroad
      SET_TO _altnames{0}.name (varchar(200)) = @Value(_primname) Mile Marker @Value(DM_Value)
      SET_TO _altnames{1}.name (varchar(200)) = @Value(_primname) MM @Value(DM_Value)
      SET_TO _altnames{2}.name (varchar(200)) = @Value(_primname) Marker @Value(DM_Value)
      SET_TO _altnames{3}.name (varchar(200)) = @Value(_primname) Milepost @Value(DM_Value)
      SET_TO _altnames{4}.name (varchar(200)) = @Value(_primname) MP @Value(DM_Value)
      SET_TO _altnames{5}.name (varchar(200)) = @Value(_primname) Post @Value(DM_Value)
      SET_TO _altnames{6}.name (varchar(200)) = @Value(_primname) Mile @Value(DM_Value)
      SET_TO _altnames{7}.name (varchar(200)) = @Value(_primname) @Value(DM_Value)
      REMOVE DiscrpAgID (varchar(100))
      SET_TO _altnames{8}.name (varchar(200)) = Mile Marker @Value(DM_Value) @Value(_primname)
      SET_TO _altnames{9}.name (varchar(200)) = MM @Value(DM_Value) @Value(_primname)
      SET_TO _altnames{10}.name (varchar(200)) = Marker @Value(DM_Value) @Value(_primname)
      SET_TO _altnames{11}.name (varchar(200)) = Milepost @Value(DM_Value) @Value(_primname)
      SET_TO _altnames{12}.name (varchar(200)) = MP @Value(DM_Value) @Value(_primname)
      SET_TO _altnames{13}.name (varchar(200)) = Post @Value(DM_Value) @Value(_primname)
      SET_TO _altnames{14}.name (varchar(200)) = Mile @Value(DM_Value) @Value(_primname)
      SET_TO _altnames{15}.name (varchar(200)) = @Value(DM_Value) @Value(_primname)
      REMOVE DateUpdate (datetime)
      SET_TO _altnames{16}.name (varchar(200)) = @Value(_altname0) Mile Marker @Value(DM_Value)
      SET_TO _altnames{17}.name (varchar(200)) = @Value(_altname0) MM @Value(DM_Value)
      SET_TO _altnames{18}.name (varchar(200)) = @Value(_altname0) Marker @Value(DM_Value)
      SET_TO _altnames{19}.name (varchar(200)) = @Value(_altname0) Milepost @Value(DM_Value)
      SET_TO _altnames{20}.name (varchar(200)) = @Value(_altname0) MP @Value(DM_Value)
      SET_TO _altnames{21}.name (varchar(200)) = @Value(_altname0) Post @Value(DM_Value)
      SET_TO _altnames{22}.name (varchar(200)) = @Value(_altname0) Mile @Value(DM_Value)
      SET_TO _altnames{23}.name (varchar(200)) = @Value(_altname0) @Value(DM_Value)
      REMOVE DM_Unit (varchar(15))
      SET_TO _altnames{24}.name (varchar(200)) = Mile Marker @Value(DM_Value) @Value(_altname0)
      SET_TO _altnames{25}.name (varchar(200)) = MM @Value(DM_Value) @Value(_altname0)
      SET_TO _altnames{26}.name (varchar(200)) = Marker @Value(DM_Value) @Value(_altname0)
      SET_TO _altnames{27}.name (varchar(200)) = Milepost @Value(DM_Value) @Value(_altname0)
      SET_TO _altnames{28}.name (varchar(200)) = MP @Value(DM_Value) @Value(_altname0)
      SET_TO _altnames{29}.name (varchar(200)) = Post @Value(DM_Value) @Value(_altname0)
      SET_TO _altnames{30}.name (varchar(200)) = Mile @Value(DM_Value) @Value(_altname0)
      SET_TO _altnames{31}.name (varchar(200)) = @Value(DM_Value) @Value(_altname0)
      REMOVE DM_Value (number(9,3))
      REMOVE DM_Type (varchar(50))
      REMOVE DM_Ind (varchar(1))
      REMOVE DM_Label (varchar(100))
      REMOVE Area (varchar(100))
      REMOVE _primname (varchar(200))
      REMOVE _altname0 (varchar(200))
      REMOVE DM_Rte (varchar(100))
    -> ListExploder_8
ListExploder_8
    ATTR_CONFLICT_RES_LOOKUP = INCOMING_IF_CONFLICT
    INDEX_ATTR = _element_index
    LIST_ATTR = _altnames{}
    ATTR_ACCUM_MODE = Merge List Attributes
    ATTR_CONFLICT_RES = Use List Attribute Values
    ELEMENTS -> remove_geometry_8
remove_geometry_8: GeometryRemover
    GEOM_NAME_SELECTION = FME_ALL_GEOMETRIES
    REMOVE_COORDSYS = Yes
    -> clean_up_fields_8
clean_up_fields_8: AttributeRemover
    REMOVE_ATTRS = _element_index,AltLabel1,AltLabel2,AltLabel3,AltLabel4,AltLabel5,AltLabel6,AltLabel7
    -> Junction_6

Bookmark: Writers - ArcGIS Online
DistanceMarkers (writer SAFE.ESRI-AGOL.ARCGISFEATURESERVICE_3)
    attributes: DiscrpAgID String(100), DateUpdate Date, NGUID String(254), DM_Unit String(15), DM_Value Double, DM_Rte String(100), DM_Type String(50), DM_Ind String(1), DM_Label String(100), Area String(100)

FME custom transformer Alphanumeric Markers
Replace the text in alphanumeric distance markers with a numeric equivalent. Workaround that's needed for the endpoint requiring an all-numeric data type

Parameters:
- DM_VALUE = @Value(DM_Value)   # Dm Value
- _MARKER_PT1 = @Value(_marker_pt1)   # Marker Pt1
- _MARKER_PT2 = @Value(_marker_pt2)   # Marker Pt2

Input (input)
    -> replace_str_with_00
replace_str_with_00: AttributeCreator
    ATTR_TABLE = SET_TO DM_Value (number(9,3)) = FME_CONDITIONAL:DEFAULT_VALUE'ERROR'BOOL_OP;OR;COMPOSITE_TEST;1;CASE_SENSITIVE_TEST @Value(_marker_pt1) CONTAINS_REGEX [a-zA-Z]'@ReplaceRegularExpression(@Value(_marker_pt1),[a-zA-Z],"",caseSensitive=FALSE).00@Value(_marker_pt2)'FME_NUM_CONDITIONS2___
    INPUT_PORT_CONNECTED = CONNECTED
    -> Output (output)
    -> if_error
Output (output)
if_error: Tester
    BOOL_OP = OR
    TEST_CLAUSE = TEST @Value(DM_Value) = ERROR
    TEST_MODE = TEST
    PASSED -> Error (output)
Error (output)

FME custom transformer GET from REST

Parameters:
- GROUP_1 =   # REST endpoint URL
- TARGET_URL = https://services2.arcgis.com/nf3p7v7Zy4fTOh6M/arcgis/rest/services/Mile_Marker/FeatureServer/0   # Request URL
- MESSAGE_1 =
- GROUP_2 =   # Where query
- WHERE_QUERY = COUNTY=79   # Where query
- MESSAGE_2 =

Note: Put these two separate results in one so we can do dynamic calculations. Using the http status field to match because that's guaranteed to match (same source) and both streams are complimentary
join_to_one_record: FeatureJoiner
    ATTR_CONFLICT_RES = USE_LEFT
    GEOMETRY_HANDLING = USE_LEFT
    JOIN_KEYS = _http_status_code _http_status_code AUTO
    JOIN_MODE = Full
    JOINED -> calc_no_of_pages
    <REJECTED> -> Junction
Note: Calculate the number of pages/http requests to send based on the max number of features being requested and the maxfeaturecount (page size). This tells us how many requests to send in order to get all features back
calc_no_of_pages: ExpressionEvaluator
    ATTRCHOICE_ACTION = OUTGOING
    EXPRESSION = ceil(@Value(_count) / @Value(_page_size))
    VAL_ATTR = _pages
    ACTION = Create New Attribute
    -> clone_based_on_pages
Note: Use a cloner to create as many instances as there are pages to request
clone_based_on_pages: Cloner
    COPIES = @Value(_pages)
    COPYATT = _copynum
    COPY -> calc_offset
Note: Calculate the offset value to embed in the GET request
calc_offset: ExpressionEvaluator
    ATTRCHOICE_ACTION = OUTGOING
    EXPRESSION = @Value(_copynum) * @Value(_page_size)
    VAL_ATTR = _offset
    ACTION = Create New Attribute
    -> GET_data
Note: Send GET query with pagination fully enabled to fetch all features
GET_data: HTTPCaller
    ADDITIONAL_URL_PARAMETERS = where;$(WHERE_QUERY) outFields;* returnGeometry;true orderByFields;OBJECTID resultOffset;@Value(_offset) resultRecordCount;@Value(_page_size) f;geojson
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(TARGET_URL)/query
    TEST_DIALOG_PARAMETERS_FOR_RESPONSE = authConnection;<Unused> authEnabled;false authMethod;<Unused> authPassword;<Unused> authUsername;<Unused> contentType;<Unused> method;GET multipartContentType;<Unused> queryParams:f;geojson queryParams:outFields;* queryParams:returnGeometry;true queryParams:where;COUNTY=79 requestUrl;https://services2.arcgis.com/nf3p7v7Zy4fTOh6M/arcgis/rest/services/Mile_Marker/FeatureServer/0/query uploadData;<Unused> verifySslCert;Yes version;HTTP_2
    TEST_DIALOG_RESPONSE_PREVIEW =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
    TEST_DIALOG_RESPONSE_STATUS:
      HTTP/2 200
      Download Size: 136239 bytes
      Total Transfer Time: 582 ms
    TRANSFER_TIMEOUT_LENGTH = 90
    USE_COOKIES = No
    VERIFY_SSL_CERTIFICATES = Yes
    -> split_data_json
    <REJECTED> -> Junction
Note: Split JSON elements in response
split_data_json: JSONFragmenter
    EXPLODE_FORMAT = GEOJSON
    EXTRACT_ATTR = No
    INPUT_PORT_CONNECTED = CONNECTED
    JSON_ATTR = _response_body
    JSON_QUERY = json[*]
    READ_FROM_FILE = NO
    REJECT_EMPTY_LISTS = YES
    FRAGMENTS -> select_features
Note: Select features (separate streams because of paginated requests)
select_features: Tester
    BOOL_OP = OR
    TEST_CLAUSE = TEST @Value(json_index) = features
    TEST_MODE = TEST
    PASSED -> JSONFragmenter
Note: Extract features from the response body
JSONFragmenter
    EXPLODE_FORMAT = GEOJSON
    EXTRACT_ATTR = Yes
    INPUT_PORT_CONNECTED = CONNECTED
    JSON_ATTR = _response_body
    JSON_QUERY = json[*]
    PREF_STRING = _s_
    READ_FROM_FILE = NO
    RECURSIVE = YES
    REJECT_EMPTY_LISTS = YES
    FRAGMENTS -> JSONExtractor
Note: Extract geometry from feature set
JSONExtractor
    EXTRACT_QUERY_TABLE = _geom json["geometry"]
    INPUT_PORT_CONNECTED = CONNECTED
    JSON_DOCUMENT = @Value(_response_body)
    READ_FROM_FILE = NO
    EVALUATED -> GeometryReplacer
Note: Set the geometry
GeometryReplacer
    KIND = GEOJSON
    REMOVE_ATTRIBUTE = Yes
    SOURCE = @Value(_geom)
    KIND_LONG = GeoJSON
    -> Output (output)
Output (output)
Junction
    -> failed_GET
Note: Interested in exactly TWO metadata attributes: / maxRecordCount as _page_size. This dynamically reports the configured max record count (in case it's different than the standard 2000). / count as _count. This reports the actual number of records that will be fetched
failed_GET: Terminator
    MESSAGE:
      Translation Terminated.

      One or more http caller failed to send a GET request

Bookmark: Send a GET request to REST endpoint to fetch metadata
GET_page_size: HTTPCaller
    ADDITIONAL_URL_PARAMETERS = where;$(WHERE_QUERY) f;json
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _page_size
    TARGET_ATTR_ENCODING = auto-detect
    TARGET_URL = $(TARGET_URL)
    TEST_DIALOG_PARAMETERS_FOR_RESPONSE = authConnection;<Unused> authEnabled;false authMethod;<Unused> authPassword;<Unused> authUsername;<Unused> contentType;<Unused> method;GET multipartContentType;<Unused> queryParams:f;geojson queryParams:outFields;* queryParams:returnGeometry;true queryParams:where;COUNTY=79 requestUrl;https://services2.arcgis.com/nf3p7v7Zy4fTOh6M/arcgis/rest/services/Mile_Marker/FeatureServer/0/query uploadData;<Unused> verifySslCert;Yes version;HTTP_2
    TEST_DIALOG_RESPONSE_PREVIEW =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
    TEST_DIALOG_RESPONSE_STATUS:
      HTTP/2 200
      Download Size: 136239 bytes
      Total Transfer Time: 582 ms
    TRANSFER_TIMEOUT_LENGTH = 90
    USE_COOKIES = No
    VERIFY_SSL_CERTIFICATES = Yes
    -> split_page_size_json
    <REJECTED> -> Junction
split_page_size_json: JSONFragmenter
    EXPLODE_FORMAT = JSON
    EXTRACT_ATTR = No
    INPUT_PORT_CONNECTED = CONNECTED
    JSON_ATTR = _page_size
    JSON_QUERY = json[*]
    READ_FROM_FILE = NO
    REJECT_EMPTY_LISTS = YES
    FRAGMENTS -> select_page_size
select_page_size: Tester
    BOOL_OP = OR
    TEST_CLAUSE = TEST @Value(json_index) = maxRecordCount
    TEST_MODE = TEST
    PASSED -> join_to_one_record [LEFT]
GET_count: HTTPCaller
    ADDITIONAL_URL_PARAMETERS = where;$(WHERE_QUERY) returnCountOnly;true f;json
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _count
    TARGET_ATTR_ENCODING = auto-detect
    TARGET_URL = $(TARGET_URL)/query
    TEST_DIALOG_PARAMETERS_FOR_RESPONSE = authConnection;<Unused> authEnabled;false authMethod;<Unused> authPassword;<Unused> authUsername;<Unused> contentType;<Unused> method;GET multipartContentType;<Unused> queryParams:f;json queryParams:returnCountOnly;true queryParams:where;COUNTY=79 requestUrl;https://services2.arcgis.com/nf3p7v7Zy4fTOh6M/arcgis/rest/services/Mile_Marker/FeatureServer/0 uploadData;<Unused> verifySslCert;Yes version;HTTP_2
    TEST_DIALOG_RESPONSE_PREVIEW = { 	"advancedEditingCapabilities": { 		"supportedApplyEditsUploadIDFormats": "JSON,PBF", 		"supportedSqlFormatsInCalculate": [ 			"standard" 		], 		"supportsApplyEditsbyUploadID": true, 		"supportsAsyncApplyEdits": true, 		"supportsMaxTranslations": 10, 		"supportsReturnEditResults": true, 		"supportsTranslation": false 	}, 	"advancedQueryAnalyticCapabilities": { 		"supportsAsync": true, 		"supportsLinearRegression": true, 		"supportsPercentileAnalytic": true, 		"supportsTrendlineRegression": true 	}, 	"advancedQueryCapabilities": { 		"fullTextSearchCapabilities": { 			"supportsAccentSensitivity": true, 			"supportsOperator": true, 			"supportsSearchOperator": true, 			"supportsStopWords": true 		}, 		"supportedLodTypes": [ 			"geohash" 		], 		"supportedOperationsWithCacheHint": [ 			"query", 			"queryTopFilter", 			"queryAnalytics", 			"queryAttachments", 			"queryRelated", 			"queryBins", 			"queryPivot" 		], 		"supportedSpatialAggregationStatistics": [ 			"EnvelopeAggregate", 			"CentroidAggregate", 			"ConvexHullAggregate" 		], 		"supportsAdvancedQueryRelated": true, 		"supportsAggIds": true, 		"supportsApproxPercentileStatistics": true, 		"supportsCountDistinct": true, 		"supportsCurrentUserQueries": true, 		"supportsDefaultSR": true, 		"supportsDisjointSpatialRel": true, 		"supportsDistinct": true, 		"supportsFullTextSearch": true, 		"supportsHavingClause": true, 		"supportsISODOW": true, 		"supportsISOWeek": true, 		"supportsLod": true, 		"supportsMaxRecordCountFactor": true, 		"supportsOrderBy": true, 		"supportsOutDistance": true, 		"supportsOutFieldSQLExpression": true, 		"supportsPagination": true, 		"supportsPaginationOnAggregatedQueries": true, 		"supportsPercentileStatistics": true, 		"supportsQueryAnalytic": true, 		"supportsQueryBins": true, 		"supportsQueryPivot": true, 		"supportsQueryRelatedPagination": true, 		"supportsQueryWithCacheHint": true, 		"supportsQueryWithCollation": true, 		"supportsQueryWithDatumTransformation": true, 		"supportsQueryWithDistance": true, 		"supportsQueryWithLodSR": false, 		"supportsQueryWithResultType": true, 		"supportsReturningGeometryCentroid": false, 		"supportsReturningGeometryEnvelope": false, 		"supportsReturningQueryExtent": true, 		"supportsSpatialAggregationStatistics": true, 		"supportsSqlExpression": true, 		"supportsStatistics": true, 		"supportsTimeRelation": true, 		"supportsTopFeaturesQuery": true, 		"supportsTranslations": false 	}, 	"allowGeometryUpdates": true, 	"cacheMaxAge": 30, 	"capabilities": "Query,Extract", 	"collation": { 		"accentSensitive": true, 		"caseSensitive": false, 		"locale": "neutral" 	}, 	"copyrightText": "", 	"currentVersion": 12, 	"dateFieldsTimeReference": { 		"respectsDaylightSaving": false, 		"timeZone": "UTC", 		"timeZoneIANA": "Etc/UTC" 	}, 	"defaultVisibility": true, 	"description": "<DIV STYLE=\"text-align:Left;\"><DIV><P><SPAN>This dataset contains single points representing the flat sheet signs (as defined by TDOT) located in Tennessee. The lines are derived from collected LIDAR data of state maintained roads. Roadview Inc. performed this data collection under the direction of TDOT. This data was created for TDOT and intended for their use.</SPAN></P></DIV></DIV>", 	"displayField": "ROUTE_NAME", 	"drawingInfo": { 		"renderer": { 			"symbol": { 				"angle": 0, 				"color": [ 					0, 					197, 					255, 					255 				], 				"outline": { 					"color": [ 						0, 						0, 						0, 						255 					], 					"style": "esriSLSSolid", 					"type": "esriSLS", 					"width": 0.7 				}, 				"size": 4, 				"style": "esriSMSCircle", 				"type": "esriSMS", 				"xoffset": 0, 				"yoffset": 0 			}, 			"type": "simple" 		}, 		"transparency": 0 	}, 	"editingInfo": { 		"dataLastEditDate": 1768425246339, 		"lastEditDate": 1768425246339, 		"schemaLastEditDate": 1768425246339 	}, 	"enableNullGeometry": false, 	"enableZDefaults": true, 	"extent": { 		"spatialReference": { 			"latestWkid": 2274, 			"wkid": 102736 		}, 		"xmax": 3233317.582129389, 		"xmin": 732427.4303763955, 		"ymax": 856695.1206584573, 		"ymin": 237000.37284570932 	}, 	"fields": [ 		{ 			"alias": "OBJECTID", 			"defaultValue": null, 			"domain": null, 			"editable": false, 			"name": "OBJECTID", 			"nullable": false, 			"sqlType": "sqlTypeOther", 			"type": "esriFieldTypeOID" 		}, 		{ 			"alias": "Reference Number", 			"defaultValue": null, 			"domain": null, 			"editable": false, 			"length": 25, 			"name": "REF_NO", 			"nullable": true, 			"sqlType": "sqlTypeOther", 			"type": "esriFieldTypeString" 		}, 		{ 			"alias": "County", 			"defaultValue": null, 			"domain": null, 			"editable": false, 			"length": 2, 			"name": "COUNTY", 			"nullable": true, 			"sqlType": "sqlTypeOther", 			"type": "esriFieldTypeString" 		}, 		{ 			"alias": "Route", 			"defaultValue": null, 			"domain": null, 			"editable": false, 			"length": 5, 			"name": "ROUTE", 			"nullable": true, 			"sqlType": "sqlTypeOther", 			"type": "esriFieldTypeString" 		}, 		{ 			"alias": "Special", 			"defaultValue": null, 			"domain": null, 			"editable": false, 			"length": 1, 			"name": "SPECIAL", 			"nullable": true, 			"sqlType": "sqlTypeOther", 			"type": "esriFieldTypeString" 		}, 		{ 			"alias": "Sequence", 			"defaultValue": null, 			"domain": null, 			"editable": false, 			"length": 2, 			"name": "SEQUENCE", 			"nullable": true, 			"sqlType": "sqlTypeOther", 			"type": "esriFieldTypeString" 		}, 		{ 			"alias": "Exit", 			"defaultValue": null, 			"domain": null, 			"editable": false, 			"length": 5, 			"name": "EXIT_", 			"nullable": true, 			"sqlType": "sqlTypeOther", 			"type": "esriFieldTypeString" 		}, 		{ 			"alias": "Ramp", 			"defaultValue": null, 			"domain": null, 			"editable": false, 			"length": 2, 			"name": "RAMP", 			"nullable": true, 			"sqlType": "sqlTypeOther", 			"type": "esriFieldTypeString" 		}, 		{ 			"alias": "Log Mile", 			"defaultValue": null, 			"domain": null, 			"editable": false, 			"name": "LOG_MILE", 			"nullable": true, 			"sqlType": "sqlTypeOther", 			"type": "esriFieldTypeSingle" 		}, 		{ 			"alias": "Marker", 			"defaultValue": null, 			"domain": null, 			"editable": false, 			"name": "MARKER", 			"nullable": true, 			"sqlType": "sqlTypeOther", 			"type": "esriFieldTypeDouble" 		}, 		{ 			"alias": "Feature Type", 			"defaultValue": null, 			"domain": null, 			"editable": false, 			"length": 2, 			"name": "FEAT_TYPE", 			"nullable": true, 			"sqlType": "sqlTypeOther", 			"type": "esriFieldTypeString" 		}, 		{ 			"alias": "Feature Character Code", 			"defaultValue": null, 			"domain": null, 			"editable": false, 			"length": 5, 			"name": "FEAT_CHAR", 			"nullable": true, 			"sqlType": "sqlTypeOther", 			"type": "esriFieldTypeString" 		}, 		{ 			"alias": "MUTCD", 			"defaultValue": null, 			"domain": null, 			"editable": false, 			"length": 25, 			"name": "MUTCD", 			"nullable": true, 			"sqlType": "sqlTypeOther", 			"type": "esriFieldTypeString" 		}, 		{ 			"alias": "Feature Description", 			"defaultValue": null, 			"domain": null, 			"editable": false, 			"length": 254, 			"name": "FEAT_DESC", 			"nullable": true, 			"sqlType": "sqlTypeOther", 			"type": "esriFieldTypeString" 		}, 		{ 			"alias": "Location", 			"defaultValue": null, 			"domain": null, 			"editable": false, 			"name": "LOCATION", 			"nullable": true, 			"sqlType": "sqlTypeOther", 			"type": "esriFieldTypeSmallInteger" 		}, 		{ 			"alias": "Location Description", 			"defaultValue": null, 			"domain": null, 			"editable": false, 			"length": 25, 			"name": "LOC_DESC", 			"nullable": true, 			"sqlType": "sqlTypeOther", 			"type": "esriFieldTypeString" 		}, 		{ 			"alias": "Condition", 			"defaultValue": null, 			"domain": null, 			"editable": false, 			"name": "CONDITION", 			"nullable": true, 			"sqlType": "sqlTypeOther", 			"type": "esriFieldTypeSmallInteger" 		}, 		{ 			"alias": "Height", 			"defaultValue": null, 			"domain": null, 			"editable": false, 			"name": "HEIGHT", 			"nullable": true, 			"sqlType": "sqlTypeOther", 			"type": "esriFieldTypeSingle" 		}, 		{ 			"alias": "Width", 			"defaultValue": null, 			"domain": null, 			"editable": false, 			"name": "WIDTH", 			"nullable": true, 			"sqlType": "sqlTypeOther", 			"type": "esriFieldTypeSingle" 		}, 		{ 			"alias": "Sign Orientation", 			"defaultValue": null, 			"domain": null, 			"editable": false, 			"name": "SIGN_ORIEN", 			"nullable": true, 			"sqlType": "sqlTypeOther", 			"type": "esriFieldTypeSmallInteger" 		}, 		{ 			"alias": "Sign Mount", 			"defaultValue": null, 			"domain": null, 			"editable": false, 			"name": "SIGN_MOUNT", 			"nullable": true, 			"sqlType": "sqlTypeOther", 			"type": "esriFieldTypeSmallInteger" 		}, 		{ 			"alias": "Comments", 			"defaultValue": null, 			"domain": null, 			"editable": false, 			"length": 254, 			"name": "COMMENTS", 			"nullable": true, 			"sqlType": "sqlTypeOther", 			"type": "esriFieldTypeString" 		}, 		{ 			"alias": "Date Collected", 			"defaultValue": null, 			"domain": null, 			"editable": false, 			"length": 8, 			"name": "DATE_COLL", 			"nullable": true, 			"precision": 1, 			"sqlType": "sqlTypeOther", 			"type": "esriFieldTypeDate" 		}, 		{ 			"alias": "Retro Reflectivity", 			"defaultValue": null, 			"domain": null, 			"editable": false, 			"name": "RETRO", 			"nullable": true, 			"sqlType": "sqlTypeOther", 			"type": "esriFieldTypeDouble" 		}, 		{ 			"alias": "Route Name", 			"defaultValue": null, 			"domain": null, 			"editable": false, 			"length": 25, 			"name": "ROUTE_NAME", 			"nullable": true, 			"sqlType": "sqlTypeOther", 			"type": "esriFieldTypeString" 		}, 		{ 			"alias": "Delivery", 			"defaultValue": null, 			"domain": null, 			"editable": false, 			"length": 50, 			"name": "DELIVERY", 			"nullable": true, 			"sqlType": "sqlTypeOther", 			"type": "esriFieldTypeString" 		}, 		{ 			"alias": "Latitude", 			"defaultValue": null, 			"domain": null, 			"editable": false, 			"name": "LATITUDE", 			"nullable": true, 			"sqlType": "sqlTypeOther", 			"type": "esriFieldTypeDouble" 		}, 		{ 			"alias": "Longitude", 			"defaultValue": null, 			"domain": null, 			"editable": false, 			"name": "LONGITUDE", 			"nullable": true, 			"sqlType": "sqlTypeOther", 			"type": "esriFieldTypeDouble" 		}, 		{ 			"alias": "Elevation", 			"defaultValue": null, 			"domain": null, 			"editable": false, 			"name": "ELEVATION", 			"nullable": true, 			"sqlType": "sqlTypeOther", 			"type": "esriFieldTypeDouble" 		} 	], 	"geometryType": "esriGeometryPoint", 	"globalIdField": "", 	"guidFormat": "", 	"hasAttachments": false, 	"hasContingentValuesDefinition": false, 	"hasM": false, 	"hasMetadata": true, 	"hasStaticData": true, 	"hasZ": true, 	"htmlPopupType": "esriServerHTMLPopupTypeAsHTMLText", 	"id": 0, 	"indexes": [ 		{ 			"description": "clustered, unique, primary key", 			"fields": "OBJECTID", 			"indexType": "Attribute", 			"isAscending": true, 			"isUnique": true, 			"name": "PK__FLAT_SHE__F4B70D85FAB90B1F" 		}, 		{ 			"description": "Shape Index", 			"fields": "Shape", 			"indexType": "Spatial", 			"isAscending": false, 			"isUnique": false, 			"name": "user_30241.FLAT_SHEET_SIGN_FLAT_SHEET_SIGN_Shape_sidx" 		}, 		{ 			"description": "MUTCD_Index", 			"fields": "MUTCD", 			"indexType": "Attribute", 			"isAscending": true, 			"isUnique": false, 			"name": "MUTCD_Index" 		}, 		{ 			"description": "FEAT_DESC_Index", 			"fields": "FEAT_DESC", 			"indexType": "Attribute", 			"isAscending": true, 			"isUnique": false, 			"name": "FEAT_DESC_Index" 		} 	], 	"infoInEstimates": [ 		"extent", 		"count" 	], 	"isDataVersioned": false, 	"isUpdatableView": true, 	"isView": true, 	"maxIdsCount": 1000000, 	"maxRecordCount": 2000, 	"maxRecordCountFactor": 1, 	"maxScale": 0, 	"minScale": 0, 	"name": "Flat Sheet Sign", 	"objectIdField": "OBJECTID", 	"preferredTimeReference": null, 	"queryBinsCapabilities": { 		"supportedNormalizationTypes": [ 			"boxCox", 			"field", 			"inverse", 			"log", 			"naturalLog", 			"percentOfTotal", 			"squareRoot" 		], 		"supportedStatisticTypes": [ 			"COUNT", 			"SUM", 			"AVG", 			"VAR", 			"STDDEV", 			"MIN", 			"MAX", 			"PERCENTILE_CONT", 			"PERCENTILE_DISC", 			"APPROX_PERCENTILE_CONT", 			"APPROX_PERCENTILE_DISC", 			"CentroidAggregate", 			"EnvelopeAggregate", 			"ConvexHullAggregate" 		], 		"supportsAsync": true, 		"supportsAutoIntervalBin": true, 		"supportsClassificationBin": true, 		"supportsDateBin": true, 		"supportsFirstDayOfWeek": true, 		"supportsFixedBoundariesBin": true, 		"supportsFixedIntervalBin": true, 		"supportsNormalization": true, 		"supportsReturnFullIntervalBin": true, 		"supportsReturnStackValueRange": true, 		"supportsSnapToData": true, 		"supportsSplitBy": true, 		"supportsStackBy": true 	}, 	"relationships": [ 	], 	"serviceItemId": "b51d9940cb7c4f6491c7b794c2037a64", 	"sourceSchemaChangesAllowed": true, 	"spatialReference": { 		"latestWkid": 2274, 		"wkid": 102736 	}, 	"standardMaxRecordCount": 16000, 	"standardMaxRecordCountNoGeometry": 32000, 	"supportedAppendFormats": "sqlite,geoPackage,shapefile,filegdb,featureCollection,geojson,csv,excel,jsonl,featureService,pbf", 	"supportedAppendSourceFilterFormats": "sqlite,geoPackage,shapefile,filegdb,featureService", 	"supportedContingentValuesFormats": "JSON, PBF", 	"supportedConvertContentFormats": "LayerEditCollection,FeatureCollection", 	"supportedConvertFileFormats": "JSON,PBF,Parquet", 	"supportedExportFormats": "csv,shapefile,sqlite,geoPackage,filegdb,featureCollection,geojson,kml,excel,parquet", 	"supportedOperationsWithCollation": "query,addField,updateField", 	"supportedQueryFormats": "JSON, geoJSON, PBF", 	"supportedSpatialRelationships": [ 		"esriSpatialRelIntersects", 		"esriSpatialRelContains", 		"esriSpatialRelCrosses", 		"esriSpatialRelEnvelopeIntersects", 		"esriSpatialRelIndexIntersects", 		"esriSpatialRelOverlaps", 		"esriSpatialRelTouches", 		"esriSpatialRelWithin", 		"esriSpatialRelDisjoint", 		"esriSpatialRelRelation" 	], 	"supportedSyncDataOptions": 260, 	"supportsASyncCalculate": true, 	"supportsAdvancedQueries": true, 	"supportsAppend": true, 	"supportsApplyEditsWithGlobalIds": false, 	"supportsAttachmentsByUploadId": true, 	"supportsAttachmentsResizing": true, 	"supportsCalculate": true, 	"supportsColumnStoreIndex": true, 	"supportsContingentValues": true, 	"supportsCoordinatesQuantization": true, 	"supportsEditingContingentValues": true, 	"supportsExceedsLimitStatistics": true, 	"supportsFieldDescriptionProperty": true, 	"supportsFieldGroups": true, 	"supportsLayerOverrides": true, 	"supportsQuantizationEditMode": true, 	"supportsReturningQueryGeometry": true, 	"supportsRollbackOnFailureParameter": true, 	"supportsStatistics": true, 	"supportsTilesAndBasicQueriesMode": true, 	"supportsTruncate": false, 	"supportsValidateSql": true, 	"templates": [ 		{ 			"description": "", 			"drawingTool": "esriFeatureEditToolPoint", 			"name": "Flat Sheet Sign", 			"prototype": { 				"attributes": { 				} 			} 		} 	], 	"tileMaxRecordCount": 8000, 	"type": "Feature Layer", 	"typeIdField": "", 	"types": [ 	], 	"uniqueIdField": { 		"isSystemMaintained": true, 		"name": "OBJECTID" 	}, 	"useStandardizedQueries": true, 	"viewSourceHasAttachments": false, 	"zDefault": 0 }
    TEST_DIALOG_RESPONSE_STATUS:
      HTTP/2 200
      Download Size: 3435 bytes
      Total Transfer Time: 270 ms
    TRANSFER_TIMEOUT_LENGTH = 90
    USE_COOKIES = No
    VERIFY_SSL_CERTIFICATES = Yes
    -> split_count_json
    <REJECTED> -> Junction
split_count_json: JSONFragmenter
    EXPLODE_FORMAT = JSON
    EXTRACT_ATTR = No
    INPUT_PORT_CONNECTED = CONNECTED
    JSON_ATTR = _count
    JSON_QUERY = json[*]
    READ_FROM_FILE = NO
    REJECT_EMPTY_LISTS = YES
    FRAGMENTS -> select_count
select_count: Tester
    BOOL_OP = OR
    TEST_CLAUSE = TEST @Value(json_index) = count
    TEST_MODE = TEST
    PASSED -> join_to_one_record [RIGHT]
